-- **************************************************************
--
-- Common definitions
--
-- **************************************************************

S1AP-CommonDataTypes {
itu-t (0) identified-organization (4) etsi (0) mobileDomain (0)
eps-Access (21) modules (3) s1ap (1) version1 (1) s1ap-CommonDataTypes (3) }

DEFINITIONS AUTOMATIC TAGS ::=

BEGIN

Criticality     ::= ENUMERATED { reject, ignore, notify }

Presence        ::= ENUMERATED { optional, conditional, mandatory }

PrivateIE-ID    ::= CHOICE {
    local               INTEGER (0..65535),
    global              OBJECT IDENTIFIER
}

ProcedureCode       ::= INTEGER {
    id-HandoverPreparation(0),
    id-HandoverResourceAllocation(1),
    id-HandoverNotification(2),
    id-PathSwitchRequest(3),
    id-HandoverCancel(4),
    id-E-RABSetup(5),
    id-E-RABModify(6),
    id-E-RABRelease(7),
    id-E-RABReleaseIndication(8),
    id-InitialContextSetup(9),
    id-Paging(10),
    id-downlinkNASTransport(11),
    id-initialUEMessage(12),
    id-uplinkNASTransport(13),
    id-Reset(14),
    id-ErrorIndication(15),
    id-NASNonDeliveryIndication(16),
    id-S1Setup(17),
    id-UEContextReleaseRequest(18),
    id-DownlinkS1cdma2000tunneling(19),
    id-UplinkS1cdma2000tunneling(20),
    id-UEContextModification(21),
    id-UECapabilityInfoIndication(22),
    id-UEContextRelease(23),
    id-eNBStatusTransfer(24),
    id-MMEStatusTransfer(25),
    id-DeactivateTrace(26),
    id-TraceStart(27),
    id-TraceFailureIndication(28),
    id-ENBConfigurationUpdate(29),
    id-MMEConfigurationUpdate(30),
    id-LocationReportingControl(31),
    id-LocationReportingFailureIndication(32),
    id-LocationReport(33),
    id-OverloadStart(34),
    id-OverloadStop(35),
    id-WriteReplaceWarning(36),
    id-eNBDirectInformationTransfer(37),
    id-MMEDirectInformationTransfer(38),
    id-PrivateMessage(39),
    id-eNBConfigurationTransfer(40),
    id-MMEConfigurationTransfer(41),
    id-CellTrafficTrace(42),
    id-Kill(43),
    id-downlinkUEAssociatedLPPaTransport(44),
    id-uplinkUEAssociatedLPPaTransport(45),
    id-downlinkNonUEAssociatedLPPaTransport(46),
    id-uplinkNonUEAssociatedLPPaTransport(47)
} (0..255)

ProtocolExtensionID ::= INTEGER (0..65535)

ProtocolIE-ID       ::= INTEGER {
    id-MME-UE-S1AP-ID(0),
    id-HandoverType(1),
    id-Cause(2),
    id-SourceID(3),
    id-TargetID (4),
    id-eNB-UE-S1AP-ID(8),
    id-E-RABSubjecttoDataForwardingList(12),
    id-E-RABtoReleaseListHOCmd(13),
    id-E-RABDataForwardingItem(14),
    id-E-RABReleaseItemBearerRelComp(15),
    id-E-RABToBeSetupListBearerSUReq(16),
    id-E-RABToBeSetupItemBearerSUReq(17),
    id-E-RABAdmittedList(18),
    id-E-RABFailedToSetupListHOReqAck(19),
    id-E-RABAdmittedItem(20),
    id-E-RABFailedtoSetupItemHOReqAck(21),
    id-E-RABToBeSwitchedDLList(22),
    id-E-RABToBeSwitchedDLItem(23),
    id-E-RABToBeSetupListCtxtSUReq(24),
    id-TraceActivation(25),
    id-NAS-PDU(26),
    id-E-RABToBeSetupItemHOReq(27),
    id-E-RABSetupListBearerSURes(28),
    id-E-RABFailedToSetupListBearerSURes(29),
    id-E-RABToBeModifiedListBearerModReq(30),
    id-E-RABModifyListBearerModRes(31),
    id-E-RABFailedToModifyList(32),
    id-E-RABToBeReleasedList(33),
    id-E-RABFailedToReleaseList(34),
    id-E-RABItem(35),
    id-E-RABToBeModifiedItemBearerModReq(36),
    id-E-RABModifyItemBearerModRes(37),
    id-E-RABReleaseItem(38),
    id-E-RABSetupItemBearerSURes(39),
    id-SecurityContext(40),
    id-HandoverRestrictionList(41),
    id-UEPagingID(43),
    id-pagingDRX(44),
    id-TAIList(46),
    id-TAIItem(47),
    id-E-RABFailedToSetupListCtxtSURes(48),
    id-E-RABReleaseItemHOCmd(49),
    id-E-RABSetupItemCtxtSURes(50),
    id-E-RABSetupListCtxtSURes(51),
    id-E-RABToBeSetupItemCtxtSUReq(52),
    id-E-RABToBeSetupListHOReq(53),
    id-GERANtoLTEHOInformationRes(55),
    id-UTRANtoLTEHOInformationRes(57),
    id-CriticalityDiagnostics(58),
    id-Global-ENB-ID(59),
    id-eNBname(60),
    id-MMEname(61),
    id-ServedPLMNs(63),
    id-SupportedTAs(64),
    id-TimeToWait(65),
    id-uEaggregateMaximumBitrate(66),
    id-TAI(67),
    id-E-RABReleaseListBearerRelComp(69),
    id-cdma2000PDU(70),
    id-cdma2000RATType(71),
    id-cdma2000SectorID(72),
    id-SecurityKey(73),
    id-UERadioCapability(74),
    id-GUMMEI-ID(75),
    id-E-RABInformationListItem(78),
    id-Direct-Forwarding-Path-Availability(79),
    id-UEIdentityIndexValue(80),
    id-cdma2000HOStatus(83),
    id-cdma2000HORequiredIndication(84),
    id-E-UTRAN-Trace-ID(86),
    id-RelativeMMECapacity(87),
    id-SourceMME-UE-S1AP-ID(88),
    id-Bearers-SubjectToStatusTransfer-Item(89),
    id-eNB-StatusTransfer-TransparentContainer(90),
    id-UE-associatedLogicalS1-ConnectionItem(91),
    id-ResetType(92),
    id-UE-associatedLogicalS1-ConnectionListResAck(93),
    id-E-RABToBeSwitchedULItem(94),
    id-E-RABToBeSwitchedULList(95),
    id-S-TMSI(96),
    id-cdma2000OneXRAND(97),
    id-RequestType(98),
    id-UE-S1AP-IDs(99),
    id-EUTRAN-CGI(100),
    id-OverloadResponse(101),
    id-cdma2000OneXSRVCCInfo(102),
    id-E-RABFailedToBeReleasedList(103),
    id-Source-ToTarget-TransparentContainer(104),
    id-ServedGUMMEIs(105),
    id-SubscriberProfileIDforRFP(106),
    id-UESecurityCapabilities(107),
    id-CSFallbackIndicator(108),
    id-CNDomain(109),
    id-E-RABReleasedList(110),
    id-MessageIdentifier(111),
    id-SerialNumber(112),
    id-WarningAreaList(113),
    id-RepetitionPeriod(114),
    id-NumberofBroadcastRequest(115),
    id-WarningType(116),
    id-WarningSecurityInfo(117),
    id-DataCodingScheme(118),
    id-WarningMessageContents(119),
    id-BroadcastCompletedAreaList(120),
    id-Inter-SystemInformationTransferTypeEDT(121),
    id-Inter-SystemInformationTransferTypeMDT(122),
    id-Target-ToSource-TransparentContainer(123),
    id-SRVCCOperationPossible(124),
    id-SRVCCHOIndication(125),
    id-NAS-DownlinkCount(126),
    id-CSG-Id(127),
    id-CSG-IdList(128),
    id-SONConfigurationTransferECT(129),
    id-SONConfigurationTransferMCT(130),
    id-TraceCollectionEntityIPAddress(131),
    id-MSClassmark2(132),
    id-MSClassmark3(133),
    id-RRC-Establishment-Cause(134),
    id-NASSecurityParametersfromE-UTRAN(135),
    id-NASSecurityParameterstoE-UTRAN(136),
    id-DefaultPagingDRX(137),
    id-Source-ToTarget-TransparentContainer-Secondary(138),
    id-Target-ToSource-TransparentContainer-Secondary(139),
    id-EUTRANRoundTripDelayEstimationInfo(140),
    id-BroadcastCancelledAreaList(141),
    id-ConcurrentWarningMessageIndicator(142),
    id-Data-Forwarding-Not-Possible(143),
    id-ExtendedRepetitionPeriod(144),
    id-CellAccessMode(145),
    id-CSGMembershipStatus(146),
    id-LPPa-PDU(147),
    id-Routing-ID(148),
    id-Time-Synchronization-Info(149),
    id-PS-ServiceNotAvailable(150),
    id-RegisteredLAI(159)
} (0..65535)

TriggeringMessage   ::= ENUMERATED { initiating-message, successful-outcome, unsuccessfull-outcome }

END
