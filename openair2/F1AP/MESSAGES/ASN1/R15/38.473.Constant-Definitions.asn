-- **************************************************************
--
-- Constant definitions
--
-- **************************************************************

F1AP-Constants { 
itu-t (0) identified-organization (4) etsi (0) mobileDomain (0) 
ngran-access (22) modules (3) f1ap (3) version1 (1) f1ap-Constants (4) } 

DEFINITIONS AUTOMATIC TAGS ::= 

BEGIN

-- **************************************************************
--
-- IE parameter types from other modules.
--
-- **************************************************************

IMPORTS
	ProcedureCode,
	ProtocolIE-ID

FROM F1AP-CommonDataTypes;


-- **************************************************************
--
-- Elementary Procedures
--
-- **************************************************************

id-Reset									ProcedureCode ::= 0
id-F1Setup									ProcedureCode ::= 1
id-ErrorIndication							ProcedureCode ::= 2
id-gNBDUConfigurationUpdate					ProcedureCode ::= 3
id-gNBCUConfigurationUpdate					ProcedureCode ::= 4
id-UEContextSetup							ProcedureCode ::= 5
id-UEContextRelease							ProcedureCode ::= 6
id-UEContextModification					ProcedureCode ::= 7
id-UEContextModificationRequired			ProcedureCode ::= 8
id-UEMobilityCommand						ProcedureCode ::= 9
id-UEContextReleaseRequest					ProcedureCode ::= 10
id-InitialULRRCMessageTransfer				ProcedureCode ::= 11
id-DLRRCMessageTransfer						ProcedureCode ::= 12
id-ULRRCMessageTransfer						ProcedureCode ::= 13
id-privateMessage							ProcedureCode ::= 14

-- **************************************************************
--
-- Extension constants
--
-- **************************************************************

maxPrivateIEs							INTEGER ::= 65535
maxProtocolExtensions					INTEGER ::= 65535
maxProtocolIEs							INTEGER ::= 65535
-- **************************************************************
--
-- Lists
--
-- **************************************************************

maxNRARFCN								INTEGER ::= 3266667
maxnoofErrors							INTEGER ::= 256
maxnoofIndividualF1ConnectionsToReset	INTEGER ::= 65536
maxCellingNBDU							INTEGER ::= 512
maxnoofSCells							INTEGER ::= 64
maxnoofSRBs								INTEGER ::= 8
maxnoofDRBs								INTEGER ::= 64
maxnoofULTunnels						INTEGER ::= 2
maxnoofDLTunnels						INTEGER ::= 2
maxnoofBPLMNs							INTEGER ::= 6
maxnoofCandidateSpCells					INTEGER ::= 64
maxnoofPotentialSpCells					INTEGER ::= 64

-- **************************************************************
--
-- IEs
--
-- **************************************************************

id-Cause											ProtocolIE-ID ::= 0
id-Cells-Failed-to-be-Activated-List				ProtocolIE-ID ::= 1
id-Cells-Failed-to-be-Activated-List-Item			ProtocolIE-ID ::= 2
id-Cells-to-be-Activated-List						ProtocolIE-ID ::= 3
id-Cells-to-be-Activated-List-Item					ProtocolIE-ID ::= 4
id-Cells-to-be-Deactivated-List						ProtocolIE-ID ::= 5
id-Cells-to-be-Deactivated-List-Item				ProtocolIE-ID ::= 6
id-CriticalityDiagnostics							ProtocolIE-ID ::= 7
id-CUtoDURRCInformation								ProtocolIE-ID ::= 9
id-DRBs-FailedToBeModifiedConf-Item					ProtocolIE-ID ::= 10
id-DRBs-FailedToBeModifiedConf-List					ProtocolIE-ID ::= 11
id-DRBs-FailedToBeModified-Item						ProtocolIE-ID ::= 12
id-DRBs-FailedToBeModified-List						ProtocolIE-ID ::= 13
id-DRBs-FailedToBeSetup-Item						ProtocolIE-ID ::= 14
id-DRBs-FailedToBeSetup-List						ProtocolIE-ID ::= 15
id-DRBs-FailedToBeSetupMod-Item						ProtocolIE-ID ::= 16
id-DRBs-FailedToBeSetupMod-List						ProtocolIE-ID ::= 17
id-DRBs-ModifiedConf-Item							ProtocolIE-ID ::= 18
id-DRBs-ModifiedConf-List							ProtocolIE-ID ::= 19
id-DRBs-Modified-Item								ProtocolIE-ID ::= 20
id-DRBs-Modified-List								ProtocolIE-ID ::= 21
id-DRBs-Required-ToBeModified-Item					ProtocolIE-ID ::= 22
id-DRBs-Required-ToBeModified-List					ProtocolIE-ID ::= 23
id-DRBs-Required-ToBeReleased-Item					ProtocolIE-ID ::= 24
id-DRBs-Required-ToBeReleased-List					ProtocolIE-ID ::= 25
id-DRBs-Setup-Item									ProtocolIE-ID ::= 26
id-DRBs-Setup-List									ProtocolIE-ID ::= 27
id-DRBs-SetupMod-Item								ProtocolIE-ID ::= 28
id-DRBs-SetupMod-List								ProtocolIE-ID ::= 29
id-DRBs-ToBeModified-Item							ProtocolIE-ID ::= 30
id-DRBs-ToBeModified-List							ProtocolIE-ID ::= 31
id-DRBs-ToBeReleased-Item							ProtocolIE-ID ::= 32
id-DRBs-ToBeReleased-List							ProtocolIE-ID ::= 33
id-DRBs-ToBeSetup-Item								ProtocolIE-ID ::= 34
id-DRBs-ToBeSetup-List								ProtocolIE-ID ::= 35
id-DRBs-ToBeSetupMod-Item							ProtocolIE-ID ::= 36
id-DRBs-ToBeSetupMod-List							ProtocolIE-ID ::= 37
id-DRXCycle											ProtocolIE-ID ::= 38
id-DUtoCURRCInformation								ProtocolIE-ID ::= 39
id-gNB-CU-UE-F1AP-ID								ProtocolIE-ID ::= 40
id-gNB-DU-UE-F1AP-ID								ProtocolIE-ID ::= 41
id-gNB-DU-ID										ProtocolIE-ID ::= 42
id-GNB-DU-Served-Cells-Item							ProtocolIE-ID ::= 43
id-gNB-DU-Served-Cells-List							ProtocolIE-ID ::= 44
id-gNB-DU-Name										ProtocolIE-ID ::= 45
id-NRCellID											ProtocolIE-ID ::= 46
id-oldgNB-DU-UE-F1AP-ID								ProtocolIE-ID ::= 47
id-ResetType										ProtocolIE-ID ::= 48
id-ResourceCoordinationTransferContainer			ProtocolIE-ID ::= 49
id-RRCContainer										ProtocolIE-ID ::= 50
id-SCell-ToBeRemoved-Item							ProtocolIE-ID ::= 51
id-SCell-ToBeRemoved-List							ProtocolIE-ID ::= 52
id-SCell-ToBeSetup-Item								ProtocolIE-ID ::= 53
id-SCell-ToBeSetup-List								ProtocolIE-ID ::= 54
id-SCell-ToBeSetupMod-Item							ProtocolIE-ID ::= 55
id-SCell-ToBeSetupMod-List							ProtocolIE-ID ::= 56
id-Served-Cells-To-Add-Item							ProtocolIE-ID ::= 57
id-Served-Cells-To-Add-List							ProtocolIE-ID ::= 58
id-Served-Cells-To-Delete-Item						ProtocolIE-ID ::= 59
id-Served-Cells-To-Delete-List						ProtocolIE-ID ::= 60
id-Served-Cells-To-Modify-Item						ProtocolIE-ID ::= 61
id-Served-Cells-To-Modify-List						ProtocolIE-ID ::= 62
id-SpCell-ID										ProtocolIE-ID ::= 63
id-SRBID											ProtocolIE-ID ::= 64
id-SRBs-FailedToBeSetup-Item						ProtocolIE-ID ::= 65
id-SRBs-FailedToBeSetup-List						ProtocolIE-ID ::= 66
id-SRBs-FailedToBeSetupMod-Item						ProtocolIE-ID ::= 67
id-SRBs-FailedToBeSetupMod-List						ProtocolIE-ID ::= 68
id-SRBs-Required-ToBeReleased-Item					ProtocolIE-ID ::= 69
id-SRBs-Required-ToBeReleased-List					ProtocolIE-ID ::= 70
id-SRBs-ToBeReleased-Item							ProtocolIE-ID ::= 71
id-SRBs-ToBeReleased-List							ProtocolIE-ID ::= 72
id-SRBs-ToBeSetup-Item								ProtocolIE-ID ::= 73
id-SRBs-ToBeSetup-List								ProtocolIE-ID ::= 74
id-SRBs-ToBeSetupMod-Item							ProtocolIE-ID ::= 75
id-SRBs-ToBeSetupMod-List							ProtocolIE-ID ::= 76
id-TimeToWait										ProtocolIE-ID ::= 75
id-TransactionID									ProtocolIE-ID ::= 78
id-TransmissionStopIndicator						ProtocolIE-ID ::= 79
id-UE-associatedLogicalF1-ConnectionItem 			ProtocolIE-ID ::= 80
id-UE-associatedLogicalF1-ConnectionListResAck		ProtocolIE-ID ::= 81
id-gNB-CU-Name										ProtocolIE-ID ::= 82
id-SCell-FailedtoSetup-List							ProtocolIE-ID ::= 83
id-SCell-FailedtoSetup-Item							ProtocolIE-ID ::= 84
id-SCell-FailedtoSetupMod-List						ProtocolIE-ID ::= 85
id-SCell-FailedtoSetupMod-Item						ProtocolIE-ID ::= 86
id-RRCRconfigurationCompleteIndicator 				ProtocolIE-ID ::= 87
id-Active-Cells-Item								ProtocolIE-ID ::= 88
id-Active-Cells-List								ProtocolIE-ID ::= 89
id-Candidate-SpCell-List							ProtocolIE-ID ::= 90
id-Candidate-SpCell-Item							ProtocolIE-ID ::= 91
id-Potential-SpCell-List							ProtocolIE-ID ::= 92
id-Potential-SpCell-Item							ProtocolIE-ID ::= 93


END
