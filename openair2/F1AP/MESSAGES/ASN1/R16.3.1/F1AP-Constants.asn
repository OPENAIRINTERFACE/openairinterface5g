-- **************************************************************
--
-- Constant definitions
--
-- **************************************************************

F1AP-Constants { 
itu-t (0) identified-organization (4) etsi (0) mobileDomain (0) 
ngran-access (22) modules (3) f1ap (3) version1 (1) f1ap-Constants (4) } 

DEFINITIONS AUTOMATIC TAGS ::= 

BEGIN

-- **************************************************************
--
-- IE parameter types from other modules.
--
-- **************************************************************

IMPORTS
	ProcedureCode,
	ProtocolIE-ID

FROM F1AP-CommonDataTypes;


-- **************************************************************
--
-- Elementary Procedures
--
-- **************************************************************

id-Reset									ProcedureCode ::= 0
id-F1Setup									ProcedureCode ::= 1
id-ErrorIndication							ProcedureCode ::= 2
id-gNBDUConfigurationUpdate					ProcedureCode ::= 3
id-gNBCUConfigurationUpdate					ProcedureCode ::= 4
id-UEContextSetup							ProcedureCode ::= 5
id-UEContextRelease							ProcedureCode ::= 6
id-UEContextModification					ProcedureCode ::= 7
id-UEContextModificationRequired			ProcedureCode ::= 8
id-UEMobilityCommand						ProcedureCode ::= 9
id-UEContextReleaseRequest					ProcedureCode ::= 10
id-InitialULRRCMessageTransfer				ProcedureCode ::= 11
id-DLRRCMessageTransfer						ProcedureCode ::= 12
id-ULRRCMessageTransfer						ProcedureCode ::= 13
id-privateMessage							ProcedureCode ::= 14
id-UEInactivityNotification					ProcedureCode ::= 15
id-GNBDUResourceCoordination				ProcedureCode ::= 16
id-SystemInformationDeliveryCommand			ProcedureCode ::= 17
id-Paging									ProcedureCode ::= 18
id-Notify									ProcedureCode ::= 19
id-WriteReplaceWarning						ProcedureCode ::= 20
id-PWSCancel								ProcedureCode ::= 21
id-PWSRestartIndication						ProcedureCode ::= 22
id-PWSFailureIndication						ProcedureCode ::= 23
id-GNBDUStatusIndication 					ProcedureCode ::= 24
id-RRCDeliveryReport		 				ProcedureCode ::= 25
id-F1Removal								ProcedureCode ::= 26
id-NetworkAccessRateReduction				ProcedureCode ::= 27
id-TraceStart								ProcedureCode ::= 28
id-DeactivateTrace							ProcedureCode ::= 29
id-DUCURadioInformationTransfer				ProcedureCode ::= 30
id-CUDURadioInformationTransfer				ProcedureCode ::= 31
id-BAPMappingConfiguration					ProcedureCode ::= 32
id-GNBDUResourceConfiguration				ProcedureCode ::= 33
id-IABTNLAddressAllocation					ProcedureCode ::= 34
id-IABUPConfigurationUpdate					ProcedureCode ::= 35
id-resourceStatusReportingInitiation		ProcedureCode ::= 36
id-resourceStatusReporting					ProcedureCode ::= 37
id-accessAndMobilityIndication				ProcedureCode ::= 38
id-accessSuccess							ProcedureCode ::= 39
id-cellTrafficTrace 						ProcedureCode ::= 40 
id-PositioningMeasurementExchange			ProcedureCode ::= 41
id-PositioningAssistanceInformationControl	ProcedureCode ::= 42
id-PositioningAssistanceInformationFeedback	ProcedureCode ::= 43
id-PositioningMeasurementReport				ProcedureCode ::= 44
id-PositioningMeasurementAbort				ProcedureCode ::= 45
id-PositioningMeasurementFailureIndication	ProcedureCode ::= 46
id-PositioningMeasurementUpdate				ProcedureCode ::= 47
id-TRPInformationExchange					ProcedureCode ::= 48
id-PositioningInformationExchange			ProcedureCode ::= 49
id-PositioningActivation					ProcedureCode ::= 50
id-PositioningDeactivation					ProcedureCode ::= 51
id-E-CIDMeasurementInitiation				ProcedureCode ::= 52
id-E-CIDMeasurementFailureIndication		ProcedureCode ::= 53
id-E-CIDMeasurementReport					ProcedureCode ::= 54
id-E-CIDMeasurementTermination				ProcedureCode ::= 55
id-PositioningInformationUpdate				ProcedureCode ::= 56
id-ReferenceTimeInformationReport			ProcedureCode ::= 57
id-ReferenceTimeInformationReportingControl	ProcedureCode ::= 58



-- **************************************************************
--
-- Extension constants
--
-- **************************************************************

maxPrivateIEs							INTEGER ::= 65535
maxProtocolExtensions					INTEGER ::= 65535
maxProtocolIEs							INTEGER ::= 65535
-- **************************************************************
--
-- Lists
--
-- **************************************************************

maxNRARFCN								INTEGER ::= 3279165
maxnoofErrors							INTEGER ::= 256
maxnoofIndividualF1ConnectionsToReset	INTEGER ::= 65536
maxCellingNBDU							INTEGER ::= 512
maxnoofSCells							INTEGER ::= 32
maxnoofSRBs								INTEGER ::= 8
maxnoofDRBs								INTEGER ::= 64
maxnoofULUPTNLInformation				INTEGER ::= 2
maxnoofDLUPTNLInformation				INTEGER ::= 2
maxnoofBPLMNs							INTEGER ::= 6
maxnoofCandidateSpCells					INTEGER ::= 64
maxnoofPotentialSpCells					INTEGER ::= 64
maxnoofNrCellBands						INTEGER ::= 32
maxnoofSIBTypes							INTEGER ::= 32
maxnoofSITypes							INTEGER ::= 32
maxnoofPagingCells						INTEGER ::= 512
maxnoofTNLAssociations					INTEGER ::= 32
maxnoofQoSFlows							INTEGER ::= 64
maxnoofSliceItems						INTEGER ::= 1024
maxCellineNB							INTEGER ::= 256
maxnoofExtendedBPLMNs					INTEGER ::= 6
maxnoofUEIDs							INTEGER ::= 65536
maxnoofBPLMNsNR							INTEGER ::= 12
maxnoofUACPLMNs							INTEGER ::= 12
maxnoofUACperPLMN						INTEGER ::= 64
maxnoofAdditionalSIBs					INTEGER ::= 63
maxnoofslots							INTEGER ::= 5120
maxnoofTLAs								INTEGER ::=	16
maxnoofGTPTLAs							INTEGER ::=	16
maxnoofBHRLCChannels					INTEGER ::= 65536
maxnoofRoutingEntries					INTEGER ::= 1024
maxnoofIABSTCInfo						INTEGER ::= 45
maxnoofSymbols							INTEGER ::= 14
maxnoofServingCells						INTEGER ::= 32
maxnoofDUFSlots							INTEGER ::= 320
maxnoofHSNASlots						INTEGER ::= 5120
maxnoofServedCellsIAB					INTEGER ::= 512 
maxnoofChildIABNodes					INTEGER ::= 1024
maxnoofNonUPTrafficMappings				INTEGER ::= 32
maxnoofTLAsIAB							INTEGER ::= 1024
maxnoofMappingEntries					INTEGER ::= 67108864
maxnoofDSInfo							INTEGER ::= 64
maxnoofEgressLinks						INTEGER ::= 2
maxnoofULUPTNLInformationforIAB			INTEGER ::= 32678
maxnoofUPTNLAddresses					INTEGER ::= 8
maxnoofSLDRBs							INTEGER ::= 512
maxnoofQoSParaSets						INTEGER ::= 8
maxnoofPC5QoSFlows						INTEGER ::= 2048
maxnoofSSBAreas							INTEGER ::=	64
maxnoofPhysicalResourceBlocks			INTEGER ::= 275
maxnoofPhysicalResourceBlocks-1			INTEGER ::= 274
maxnoofPRACHconfigs						INTEGER ::= 16
maxnoofRACHReports						INTEGER ::= 64
maxnoofRLFReports						INTEGER ::= 64
maxnoofAdditionalPDCPDuplicationTNL		INTEGER ::=	2
maxnoofRLCDuplicationState				INTEGER ::=	3
maxnoofCHOcells							INTEGER ::= 8
maxnoofMDTPLMNs							INTEGER ::=	16
maxnoofCAGsupported						INTEGER ::= 12
maxnoofNIDsupported						INTEGER ::= 12
maxnoofNRSCSs							INTEGER ::= 5
maxnoofExtSliceItems					INTEGER ::= 65535 
maxnoofPosMeas							INTEGER ::=	16384
maxnoofTRPInfoTypes						INTEGER ::=	64 
maxnoofTRPs								INTEGER ::=	65535 
maxnoofSRSTriggerStates					INTEGER ::= 3
maxnoofSpatialRelations					INTEGER ::= 64
maxnoBcastCell							INTEGER ::= 16384
maxnoofAngleInfo						INTEGER ::= 65535
maxnooflcs-gcs-translation				INTEGER ::= 3
maxnoofPath								INTEGER ::= 2
maxnoofMeasE-CID						INTEGER ::= 64
maxnoofSSBs								INTEGER ::= 255
maxnoSRS-ResourceSets					INTEGER ::= 16
maxnoSRS-ResourcePerSet					INTEGER ::= 16
maxnoSRS-Carriers						INTEGER ::= 32
maxnoSCSs								INTEGER ::= 5
maxnoSRS-Resources						INTEGER ::= 64
maxnoSRS-PosResources					INTEGER ::= 64
maxnoSRS-PosResourceSets				INTEGER ::= 16
maxnoSRS-PosResourcePerSet				INTEGER ::= 16
maxnoofPRS-ResourceSets					INTEGER ::= 2
maxnoofPRS-ResourcesPerSet				INTEGER ::= 64
maxNoOfMeasTRPs							INTEGER ::= 64
maxnoofPRSresourceSets					INTEGER ::= 8
maxnoofPRSresources						INTEGER ::= 64



-- **************************************************************
--
-- IEs
--
-- **************************************************************

id-Cause											ProtocolIE-ID ::= 0
id-Cells-Failed-to-be-Activated-List				ProtocolIE-ID ::= 1
id-Cells-Failed-to-be-Activated-List-Item			ProtocolIE-ID ::= 2
id-Cells-to-be-Activated-List						ProtocolIE-ID ::= 3
id-Cells-to-be-Activated-List-Item					ProtocolIE-ID ::= 4
id-Cells-to-be-Deactivated-List						ProtocolIE-ID ::= 5
id-Cells-to-be-Deactivated-List-Item				ProtocolIE-ID ::= 6
id-CriticalityDiagnostics							ProtocolIE-ID ::= 7
id-CUtoDURRCInformation								ProtocolIE-ID ::= 9
id-DRBs-FailedToBeModified-Item						ProtocolIE-ID ::= 12
id-DRBs-FailedToBeModified-List						ProtocolIE-ID ::= 13
id-DRBs-FailedToBeSetup-Item						ProtocolIE-ID ::= 14
id-DRBs-FailedToBeSetup-List						ProtocolIE-ID ::= 15
id-DRBs-FailedToBeSetupMod-Item						ProtocolIE-ID ::= 16
id-DRBs-FailedToBeSetupMod-List						ProtocolIE-ID ::= 17
id-DRBs-ModifiedConf-Item							ProtocolIE-ID ::= 18
id-DRBs-ModifiedConf-List							ProtocolIE-ID ::= 19
id-DRBs-Modified-Item								ProtocolIE-ID ::= 20
id-DRBs-Modified-List								ProtocolIE-ID ::= 21
id-DRBs-Required-ToBeModified-Item					ProtocolIE-ID ::= 22
id-DRBs-Required-ToBeModified-List					ProtocolIE-ID ::= 23
id-DRBs-Required-ToBeReleased-Item					ProtocolIE-ID ::= 24
id-DRBs-Required-ToBeReleased-List					ProtocolIE-ID ::= 25
id-DRBs-Setup-Item									ProtocolIE-ID ::= 26
id-DRBs-Setup-List									ProtocolIE-ID ::= 27
id-DRBs-SetupMod-Item								ProtocolIE-ID ::= 28
id-DRBs-SetupMod-List								ProtocolIE-ID ::= 29
id-DRBs-ToBeModified-Item							ProtocolIE-ID ::= 30
id-DRBs-ToBeModified-List							ProtocolIE-ID ::= 31
id-DRBs-ToBeReleased-Item							ProtocolIE-ID ::= 32
id-DRBs-ToBeReleased-List							ProtocolIE-ID ::= 33
id-DRBs-ToBeSetup-Item								ProtocolIE-ID ::= 34
id-DRBs-ToBeSetup-List								ProtocolIE-ID ::= 35
id-DRBs-ToBeSetupMod-Item							ProtocolIE-ID ::= 36
id-DRBs-ToBeSetupMod-List							ProtocolIE-ID ::= 37
id-DRXCycle											ProtocolIE-ID ::= 38
id-DUtoCURRCInformation								ProtocolIE-ID ::= 39
id-gNB-CU-UE-F1AP-ID								ProtocolIE-ID ::= 40
id-gNB-DU-UE-F1AP-ID								ProtocolIE-ID ::= 41
id-gNB-DU-ID										ProtocolIE-ID ::= 42
id-GNB-DU-Served-Cells-Item							ProtocolIE-ID ::= 43
id-gNB-DU-Served-Cells-List							ProtocolIE-ID ::= 44
id-gNB-DU-Name										ProtocolIE-ID ::= 45
id-NRCellID											ProtocolIE-ID ::= 46
id-oldgNB-DU-UE-F1AP-ID								ProtocolIE-ID ::= 47
id-ResetType										ProtocolIE-ID ::= 48
id-ResourceCoordinationTransferContainer			ProtocolIE-ID ::= 49
id-RRCContainer										ProtocolIE-ID ::= 50
id-SCell-ToBeRemoved-Item							ProtocolIE-ID ::= 51
id-SCell-ToBeRemoved-List							ProtocolIE-ID ::= 52
id-SCell-ToBeSetup-Item								ProtocolIE-ID ::= 53
id-SCell-ToBeSetup-List								ProtocolIE-ID ::= 54
id-SCell-ToBeSetupMod-Item							ProtocolIE-ID ::= 55
id-SCell-ToBeSetupMod-List							ProtocolIE-ID ::= 56
id-Served-Cells-To-Add-Item							ProtocolIE-ID ::= 57
id-Served-Cells-To-Add-List							ProtocolIE-ID ::= 58
id-Served-Cells-To-Delete-Item						ProtocolIE-ID ::= 59
id-Served-Cells-To-Delete-List						ProtocolIE-ID ::= 60
id-Served-Cells-To-Modify-Item						ProtocolIE-ID ::= 61
id-Served-Cells-To-Modify-List						ProtocolIE-ID ::= 62
id-SpCell-ID										ProtocolIE-ID ::= 63
id-SRBID											ProtocolIE-ID ::= 64
id-SRBs-FailedToBeSetup-Item						ProtocolIE-ID ::= 65
id-SRBs-FailedToBeSetup-List						ProtocolIE-ID ::= 66
id-SRBs-FailedToBeSetupMod-Item						ProtocolIE-ID ::= 67
id-SRBs-FailedToBeSetupMod-List						ProtocolIE-ID ::= 68
id-SRBs-Required-ToBeReleased-Item					ProtocolIE-ID ::= 69
id-SRBs-Required-ToBeReleased-List					ProtocolIE-ID ::= 70
id-SRBs-ToBeReleased-Item							ProtocolIE-ID ::= 71
id-SRBs-ToBeReleased-List							ProtocolIE-ID ::= 72
id-SRBs-ToBeSetup-Item								ProtocolIE-ID ::= 73
id-SRBs-ToBeSetup-List								ProtocolIE-ID ::= 74
id-SRBs-ToBeSetupMod-Item							ProtocolIE-ID ::= 75
id-SRBs-ToBeSetupMod-List							ProtocolIE-ID ::= 76
id-TimeToWait										ProtocolIE-ID ::= 77
id-TransactionID									ProtocolIE-ID ::= 78
id-TransmissionActionIndicator						ProtocolIE-ID ::= 79
id-UE-associatedLogicalF1-ConnectionItem 			ProtocolIE-ID ::= 80
id-UE-associatedLogicalF1-ConnectionListResAck		ProtocolIE-ID ::= 81
id-gNB-CU-Name										ProtocolIE-ID ::= 82
id-SCell-FailedtoSetup-List							ProtocolIE-ID ::= 83
id-SCell-FailedtoSetup-Item							ProtocolIE-ID ::= 84
id-SCell-FailedtoSetupMod-List						ProtocolIE-ID ::= 85
id-SCell-FailedtoSetupMod-Item						ProtocolIE-ID ::= 86
id-RRCReconfigurationCompleteIndicator 				ProtocolIE-ID ::= 87
id-Cells-Status-Item								ProtocolIE-ID ::= 88
id-Cells-Status-List								ProtocolIE-ID ::= 89
id-Candidate-SpCell-List							ProtocolIE-ID ::= 90
id-Candidate-SpCell-Item							ProtocolIE-ID ::= 91
id-Potential-SpCell-List							ProtocolIE-ID ::= 92
id-Potential-SpCell-Item							ProtocolIE-ID ::= 93
id-FullConfiguration								ProtocolIE-ID ::= 94
id-C-RNTI											ProtocolIE-ID ::= 95
id-SpCellULConfigured								ProtocolIE-ID ::= 96
id-InactivityMonitoringRequest						ProtocolIE-ID ::= 97
id-InactivityMonitoringResponse						ProtocolIE-ID ::= 98
id-DRB-Activity-Item								ProtocolIE-ID ::= 99
id-DRB-Activity-List								ProtocolIE-ID ::= 100
id-EUTRA-NR-CellResourceCoordinationReq-Container 		ProtocolIE-ID ::= 101
id-EUTRA-NR-CellResourceCoordinationReqAck-Container 	ProtocolIE-ID ::= 102
id-Protected-EUTRA-Resources-List					ProtocolIE-ID ::= 105
id-RequestType 										ProtocolIE-ID ::= 106
id-ServCellIndex									ProtocolIE-ID ::= 107 
id-RAT-FrequencyPriorityInformation					ProtocolIE-ID ::= 108
id-ExecuteDuplication								ProtocolIE-ID ::= 109
id-NRCGI											ProtocolIE-ID ::= 111
id-PagingCell-Item									ProtocolIE-ID ::= 112
id-PagingCell-List									ProtocolIE-ID ::= 113
id-PagingDRX										ProtocolIE-ID ::= 114
id-PagingPriority 									ProtocolIE-ID ::= 115
id-SItype-List										ProtocolIE-ID ::= 116
id-UEIdentityIndexValue								ProtocolIE-ID ::= 117
id-gNB-CUSystemInformation							ProtocolIE-ID ::= 118
id-HandoverPreparationInformation					ProtocolIE-ID ::= 119
id-GNB-CU-TNL-Association-To-Add-Item				ProtocolIE-ID ::= 120
id-GNB-CU-TNL-Association-To-Add-List				ProtocolIE-ID ::= 121
id-GNB-CU-TNL-Association-To-Remove-Item			ProtocolIE-ID ::= 122
id-GNB-CU-TNL-Association-To-Remove-List			ProtocolIE-ID ::= 123
id-GNB-CU-TNL-Association-To-Update-Item			ProtocolIE-ID ::= 124
id-GNB-CU-TNL-Association-To-Update-List			ProtocolIE-ID ::= 125
id-MaskedIMEISV										ProtocolIE-ID ::= 126
id-PagingIdentity									ProtocolIE-ID ::= 127
id-DUtoCURRCContainer								ProtocolIE-ID ::= 128
id-Cells-to-be-Barred-List							ProtocolIE-ID ::= 129
id-Cells-to-be-Barred-Item							ProtocolIE-ID ::= 130
id-TAISliceSupportList								ProtocolIE-ID ::= 131
id-GNB-CU-TNL-Association-Setup-List				ProtocolIE-ID ::= 132
id-GNB-CU-TNL-Association-Setup-Item				ProtocolIE-ID ::= 133
id-GNB-CU-TNL-Association-Failed-To-Setup-List		ProtocolIE-ID ::= 134
id-GNB-CU-TNL-Association-Failed-To-Setup-Item		ProtocolIE-ID ::= 135
id-DRB-Notify-Item									ProtocolIE-ID ::= 136
id-DRB-Notify-List									ProtocolIE-ID ::= 137
id-NotficationControl								ProtocolIE-ID ::= 138
id-RANAC											ProtocolIE-ID ::= 139
id-PWSSystemInformation								ProtocolIE-ID ::= 140
id-RepetitionPeriod									ProtocolIE-ID ::= 141
id-NumberofBroadcastRequest							ProtocolIE-ID ::= 142
id-Cells-To-Be-Broadcast-List						ProtocolIE-ID ::= 144
id-Cells-To-Be-Broadcast-Item						ProtocolIE-ID ::= 145
id-Cells-Broadcast-Completed-List 					ProtocolIE-ID ::= 146
id-Cells-Broadcast-Completed-Item 					ProtocolIE-ID ::= 147
id-Broadcast-To-Be-Cancelled-List 					ProtocolIE-ID ::= 148
id-Broadcast-To-Be-Cancelled-Item 					ProtocolIE-ID ::= 149
id-Cells-Broadcast-Cancelled-List 					ProtocolIE-ID ::= 150
id-Cells-Broadcast-Cancelled-Item 					ProtocolIE-ID ::= 151
id-NR-CGI-List-For-Restart-List 					ProtocolIE-ID ::= 152
id-NR-CGI-List-For-Restart-Item 					ProtocolIE-ID ::= 153
id-PWS-Failed-NR-CGI-List 							ProtocolIE-ID ::= 154
id-PWS-Failed-NR-CGI-Item 							ProtocolIE-ID ::= 155
id-ConfirmedUEID									ProtocolIE-ID ::= 156
id-Cancel-all-Warning-Messages-Indicator			ProtocolIE-ID ::= 157
id-GNB-DU-UE-AMBR-UL								ProtocolIE-ID ::= 158
id-DRXConfigurationIndicator						ProtocolIE-ID ::= 159
id-RLC-Status										ProtocolIE-ID ::= 160
id-DLPDCPSNLength									ProtocolIE-ID ::= 161
id-GNB-DUConfigurationQuery							ProtocolIE-ID ::= 162
id-MeasurementTimingConfiguration					ProtocolIE-ID ::= 163
id-DRB-Information									ProtocolIE-ID ::= 164
id-ServingPLMN										ProtocolIE-ID ::= 165
id-Protected-EUTRA-Resources-Item					ProtocolIE-ID ::= 168
id-GNB-CU-RRC-Version								ProtocolIE-ID ::= 170
id-GNB-DU-RRC-Version								ProtocolIE-ID ::= 171
id-GNBDUOverloadInformation							ProtocolIE-ID ::= 172
id-CellGroupConfig									ProtocolIE-ID ::= 173
id-RLCFailureIndication								ProtocolIE-ID ::= 174
id-UplinkTxDirectCurrentListInformation				ProtocolIE-ID ::= 175
id-DC-Based-Duplication-Configured					ProtocolIE-ID ::= 176
id-DC-Based-Duplication-Activation					ProtocolIE-ID ::= 177
id-SULAccessIndication								ProtocolIE-ID ::= 178
id-AvailablePLMNList								ProtocolIE-ID ::= 179
id-PDUSessionID										ProtocolIE-ID ::= 180
id-ULPDUSessionAggregateMaximumBitRate				ProtocolIE-ID ::= 181
id-ServingCellMO									ProtocolIE-ID ::= 182
id-QoSFlowMappingIndication							ProtocolIE-ID ::= 183
id-RRCDeliveryStatusRequest							ProtocolIE-ID ::= 184
id-RRCDeliveryStatus								ProtocolIE-ID ::= 185
id-BearerTypeChange									ProtocolIE-ID ::= 186
id-RLCMode											ProtocolIE-ID ::= 187
id-Duplication-Activation							ProtocolIE-ID ::= 188
id-Dedicated-SIDelivery-NeededUE-List				ProtocolIE-ID ::= 189
id-Dedicated-SIDelivery-NeededUE-Item				ProtocolIE-ID ::= 190
id-DRX-LongCycleStartOffset							ProtocolIE-ID ::= 191
id-ULPDCPSNLength									ProtocolIE-ID ::= 192
id-SelectedBandCombinationIndex						ProtocolIE-ID ::= 193
id-SelectedFeatureSetEntryIndex						ProtocolIE-ID ::= 194
id-ResourceCoordinationTransferInformation			ProtocolIE-ID ::= 195
id-ExtendedServedPLMNs-List							ProtocolIE-ID ::= 196
id-ExtendedAvailablePLMN-List						ProtocolIE-ID ::= 197
id-Associated-SCell-List							ProtocolIE-ID ::= 198
id-latest-RRC-Version-Enhanced						ProtocolIE-ID ::= 199
id-Associated-SCell-Item							ProtocolIE-ID ::= 200
id-Cell-Direction									ProtocolIE-ID ::= 201
id-SRBs-Setup-List									ProtocolIE-ID ::= 202
id-SRBs-Setup-Item									ProtocolIE-ID ::= 203
id-SRBs-SetupMod-List								ProtocolIE-ID ::= 204
id-SRBs-SetupMod-Item								ProtocolIE-ID ::= 205
id-SRBs-Modified-List								ProtocolIE-ID ::= 206
id-SRBs-Modified-Item								ProtocolIE-ID ::= 207
id-Ph-InfoSCG										ProtocolIE-ID ::= 208
id-RequestedBandCombinationIndex					ProtocolIE-ID ::= 209
id-RequestedFeatureSetEntryIndex					ProtocolIE-ID ::= 210
id-RequestedP-MaxFR2								ProtocolIE-ID ::= 211
id-DRX-Config										ProtocolIE-ID ::= 212
id-IgnoreResourceCoordinationContainer				ProtocolIE-ID ::= 213
id-UEAssistanceInformation							ProtocolIE-ID ::= 214
id-NeedforGap										ProtocolIE-ID ::= 215
id-PagingOrigin										ProtocolIE-ID ::= 216
id-new-gNB-CU-UE-F1AP-ID							ProtocolIE-ID ::= 217
id-RedirectedRRCmessage								ProtocolIE-ID ::= 218
id-new-gNB-DU-UE-F1AP-ID							ProtocolIE-ID ::= 219
id-NotificationInformation							ProtocolIE-ID ::= 220
id-PLMNAssistanceInfoForNetShar						ProtocolIE-ID ::= 221
id-UEContextNotRetrievable							ProtocolIE-ID ::= 222
id-BPLMN-ID-Info-List								ProtocolIE-ID ::= 223
id-SelectedPLMNID									ProtocolIE-ID ::= 224
id-UAC-Assistance-Info								ProtocolIE-ID ::= 225
id-RANUEID											ProtocolIE-ID ::= 226
id-GNB-DU-TNL-Association-To-Remove-Item			ProtocolIE-ID ::= 227
id-GNB-DU-TNL-Association-To-Remove-List			ProtocolIE-ID ::= 228
id-TNLAssociationTransportLayerAddressgNBDU			ProtocolIE-ID ::= 229
id-portNumber										ProtocolIE-ID ::= 230
id-AdditionalSIBMessageList							ProtocolIE-ID ::= 231
id-Cell-Type										ProtocolIE-ID ::= 232
id-IgnorePRACHConfiguration							ProtocolIE-ID ::= 233
id-CG-Config										ProtocolIE-ID ::= 234
id-PDCCH-BlindDetectionSCG							ProtocolIE-ID ::= 235
id-Requested-PDCCH-BlindDetectionSCG				ProtocolIE-ID ::= 236
id-Ph-InfoMCG										ProtocolIE-ID ::= 237
id-MeasGapSharingConfig								ProtocolIE-ID ::= 238
id-systemInformationAreaID							ProtocolIE-ID ::= 239
id-areaScope										ProtocolIE-ID ::= 240
id-RRCContainer-RRCSetupComplete					ProtocolIE-ID ::= 241
id-TraceActivation									ProtocolIE-ID ::= 242
id-TraceID											ProtocolIE-ID ::= 243
id-Neighbour-Cell-Information-List					ProtocolIE-ID ::= 244
id-SymbolAllocInSlot								ProtocolIE-ID ::= 246
id-NumDLULSymbols									ProtocolIE-ID ::= 247
id-AdditionalRRMPriorityIndex						ProtocolIE-ID ::= 248
id-DUCURadioInformationType							ProtocolIE-ID ::= 249
id-CUDURadioInformationType 						ProtocolIE-ID ::= 250
id-AggressorgNBSetID								ProtocolIE-ID ::= 251
id-VictimgNBSetID									ProtocolIE-ID ::= 252
id-LowerLayerPresenceStatusChange					ProtocolIE-ID ::= 253
id-Transport-Layer-Address-Info						ProtocolIE-ID ::= 254
id-Neighbour-Cell-Information-Item					ProtocolIE-ID ::= 255
id-IntendedTDD-DL-ULConfig							ProtocolIE-ID ::= 256
id-QosMonitoringRequest								ProtocolIE-ID ::= 257
id-BHChannels-ToBeSetup-List						ProtocolIE-ID ::= 258
id-BHChannels-ToBeSetup-Item						ProtocolIE-ID ::= 259
id-BHChannels-Setup-List							ProtocolIE-ID ::= 260
id-BHChannels-Setup-Item							ProtocolIE-ID ::= 261
id-BHChannels-ToBeModified-Item						ProtocolIE-ID ::= 262
id-BHChannels-ToBeModified-List						ProtocolIE-ID ::= 263
id-BHChannels-ToBeReleased-Item						ProtocolIE-ID ::= 264
id-BHChannels-ToBeReleased-List						ProtocolIE-ID ::= 265
id-BHChannels-ToBeSetupMod-Item						ProtocolIE-ID ::= 266
id-BHChannels-ToBeSetupMod-List						ProtocolIE-ID ::= 267
id-BHChannels-FailedToBeModified-Item				ProtocolIE-ID ::= 268
id-BHChannels-FailedToBeModified-List				ProtocolIE-ID ::= 269
id-BHChannels-FailedToBeSetupMod-Item				ProtocolIE-ID ::= 270
id-BHChannels-FailedToBeSetupMod-List				ProtocolIE-ID ::= 271
id-BHChannels-Modified-Item							ProtocolIE-ID ::= 272
id-BHChannels-Modified-List							ProtocolIE-ID ::= 273
id-BHChannels-SetupMod-Item							ProtocolIE-ID ::= 274
id-BHChannels-SetupMod-List							ProtocolIE-ID ::= 275
id-BHChannels-Required-ToBeReleased-Item			ProtocolIE-ID ::= 276
id-BHChannels-Required-ToBeReleased-List			ProtocolIE-ID ::= 277
id-BHChannels-FailedToBeSetup-Item					ProtocolIE-ID ::= 278
id-BHChannels-FailedToBeSetup-List					ProtocolIE-ID ::= 279
id-BHInfo											ProtocolIE-ID ::= 280
id-BAPAddress										ProtocolIE-ID ::= 281
id-ConfiguredBAPAddress								ProtocolIE-ID ::= 282
id-BH-Routing-Information-Added-List				ProtocolIE-ID ::= 283
id-BH-Routing-Information-Added-List-Item			ProtocolIE-ID ::= 284
id-BH-Routing-Information-Removed-List				ProtocolIE-ID ::= 285
id-BH-Routing-Information-Removed-List-Item			ProtocolIE-ID ::= 286
id-UL-BH-Non-UP-Traffic-Mapping						ProtocolIE-ID ::= 287
id-Activated-Cells-to-be-Updated-List				ProtocolIE-ID ::= 288
id-Child-Nodes-List									ProtocolIE-ID ::= 289
id-IAB-Info-IAB-DU									ProtocolIE-ID ::= 290
id-IAB-Info-IAB-donor-CU							ProtocolIE-ID ::= 291
id-IAB-TNL-Addresses-To-Remove-List					ProtocolIE-ID ::= 292
id-IAB-TNL-Addresses-To-Remove-Item					ProtocolIE-ID ::= 293
id-IAB-Allocated-TNL-Address-List					ProtocolIE-ID ::= 294
id-IAB-Allocated-TNL-Address-Item					ProtocolIE-ID ::= 295
id-IABIPv6RequestType								ProtocolIE-ID ::= 296
id-IABv4AddressesRequested							ProtocolIE-ID ::= 297
id-IAB-Barred										ProtocolIE-ID ::= 298
id-TrafficMappingInformation						ProtocolIE-ID ::= 299
id-UL-UP-TNL-Information-to-Update-List				ProtocolIE-ID ::= 300
id-UL-UP-TNL-Information-to-Update-List-Item		ProtocolIE-ID ::= 301
id-UL-UP-TNL-Address-to-Update-List					ProtocolIE-ID ::= 302
id-UL-UP-TNL-Address-to-Update-List-Item			ProtocolIE-ID ::= 303
id-DL-UP-TNL-Address-to-Update-List					ProtocolIE-ID ::= 304
id-DL-UP-TNL-Address-to-Update-List-Item			ProtocolIE-ID ::= 305
id-NRV2XServicesAuthorized							ProtocolIE-ID ::= 306
id-LTEV2XServicesAuthorized							ProtocolIE-ID ::= 307
id-NRUESidelinkAggregateMaximumBitrate				ProtocolIE-ID ::= 308
id-LTEUESidelinkAggregateMaximumBitrate				ProtocolIE-ID ::= 309
id-SIB12-message									ProtocolIE-ID ::= 310
id-SIB13-message									ProtocolIE-ID ::= 311
id-SIB14-message									ProtocolIE-ID ::= 312
id-SLDRBs-FailedToBeModified-Item					ProtocolIE-ID ::= 313
id-SLDRBs-FailedToBeModified-List					ProtocolIE-ID ::= 314
id-SLDRBs-FailedToBeSetup-Item						ProtocolIE-ID ::= 315
id-SLDRBs-FailedToBeSetup-List						ProtocolIE-ID ::= 316
id-SLDRBs-Modified-Item								ProtocolIE-ID ::= 317
id-SLDRBs-Modified-List								ProtocolIE-ID ::= 318
id-SLDRBs-Required-ToBeModified-Item				ProtocolIE-ID ::= 319
id-SLDRBs-Required-ToBeModified-List				ProtocolIE-ID ::= 320
id-SLDRBs-Required-ToBeReleased-Item				ProtocolIE-ID ::= 321
id-SLDRBs-Required-ToBeReleased-List				ProtocolIE-ID ::= 322
id-SLDRBs-Setup-Item								ProtocolIE-ID ::= 323
id-SLDRBs-Setup-List								ProtocolIE-ID ::= 324
id-SLDRBs-ToBeModified-Item							ProtocolIE-ID ::= 325
id-SLDRBs-ToBeModified-List							ProtocolIE-ID ::= 326
id-SLDRBs-ToBeReleased-Item							ProtocolIE-ID ::= 327
id-SLDRBs-ToBeReleased-List							ProtocolIE-ID ::= 328
id-SLDRBs-ToBeSetup-Item							ProtocolIE-ID ::= 329
id-SLDRBs-ToBeSetup-List							ProtocolIE-ID ::= 330
id-SLDRBs-ToBeSetupMod-Item							ProtocolIE-ID ::= 331
id-SLDRBs-ToBeSetupMod-List							ProtocolIE-ID ::= 332
id-SLDRBs-SetupMod-List								ProtocolIE-ID ::= 333
id-SLDRBs-FailedToBeSetupMod-List					ProtocolIE-ID ::= 334
id-SLDRBs-SetupMod-Item								ProtocolIE-ID ::= 335
id-SLDRBs-FailedToBeSetupMod-Item					ProtocolIE-ID ::= 336
id-SLDRBs-ModifiedConf-List							ProtocolIE-ID ::= 337
id-SLDRBs-ModifiedConf-Item							ProtocolIE-ID ::= 338
id-UEAssistanceInformationEUTRA						ProtocolIE-ID ::= 339
id-PC5LinkAMBR										ProtocolIE-ID ::= 340
id-SL-PHY-MAC-RLC-Config							ProtocolIE-ID ::= 341
id-SL-ConfigDedicatedEUTRA							ProtocolIE-ID ::= 342
id-AlternativeQoSParaSetList						ProtocolIE-ID ::= 343
id-CurrentQoSParaSetIndex							ProtocolIE-ID ::= 344
id-gNBCUMeasurementID								ProtocolIE-ID ::= 345
id-gNBDUMeasurementID								ProtocolIE-ID ::= 346
id-RegistrationRequest								ProtocolIE-ID ::= 347
id-ReportCharacteristics							ProtocolIE-ID ::= 348
id-CellToReportList									ProtocolIE-ID ::= 349
id-CellMeasurementResultList						ProtocolIE-ID ::= 350
id-HardwareLoadIndicator							ProtocolIE-ID ::= 351
id-ReportingPeriodicity								ProtocolIE-ID ::= 352
id-TNLCapacityIndicator								ProtocolIE-ID ::= 353
id-CarrierList										ProtocolIE-ID ::= 354
id-ULCarrierList									ProtocolIE-ID ::= 355
id-FrequencyShift7p5khz								ProtocolIE-ID ::= 356
id-SSB-PositionsInBurst								ProtocolIE-ID ::= 357
id-NRPRACHConfig									ProtocolIE-ID ::= 358
id-RACHReportInformationList						ProtocolIE-ID ::= 359
id-RLFReportInformationList							ProtocolIE-ID ::= 360
id-TDD-UL-DLConfigCommonNR							ProtocolIE-ID ::= 361
id-CNPacketDelayBudgetDownlink						ProtocolIE-ID ::= 362
id-ExtendedPacketDelayBudget						ProtocolIE-ID ::= 363
id-TSCTrafficCharacteristics						ProtocolIE-ID ::= 364
id-ReportingRequestType								ProtocolIE-ID ::= 365
id-TimeReferenceInformation							ProtocolIE-ID ::= 366
id-CNPacketDelayBudgetUplink						ProtocolIE-ID ::= 369
id-AdditionalPDCPDuplicationTNL-List				ProtocolIE-ID ::= 370
id-RLCDuplicationInformation						ProtocolIE-ID ::= 371
id-AdditionalDuplicationIndication					ProtocolIE-ID ::= 372
id-ConditionalInterDUMobilityInformation			ProtocolIE-ID ::= 373
id-ConditionalIntraDUMobilityInformation			ProtocolIE-ID ::= 374
id-targetCellsToCancel								ProtocolIE-ID ::= 375
id-requestedTargetCellGlobalID						ProtocolIE-ID ::= 376
id-ManagementBasedMDTPLMNList						ProtocolIE-ID ::= 377
id-TraceCollectionEntityIPAddress 					ProtocolIE-ID ::= 378
id-PrivacyIndicator									ProtocolIE-ID ::= 379
id-TraceCollectionEntityURI							ProtocolIE-ID ::= 380
id-mdtConfiguration									ProtocolIE-ID ::= 381
id-ServingNID										ProtocolIE-ID ::= 382
id-NPNBroadcastInformation							ProtocolIE-ID ::= 383
id-NPNSupportInfo									ProtocolIE-ID ::= 384
id-NID												ProtocolIE-ID ::= 385
id-AvailableSNPN-ID-List							ProtocolIE-ID ::= 386
id-SIB10-message									ProtocolIE-ID ::= 387
id-DLCarrierList									ProtocolIE-ID ::= 389
	id-ExtendedTAISliceSupportList					ProtocolIE-ID ::= 390 
id-RequestedSRSTransmissionCharacteristics			ProtocolIE-ID ::= 391
id-PosAssistance-Information						ProtocolIE-ID ::= 392
id-PosBroadcast										ProtocolIE-ID ::= 393
id-RoutingID										ProtocolIE-ID ::= 394
id-PosAssistanceInformationFailureList				ProtocolIE-ID ::= 395
id-PosMeasurementQuantities							ProtocolIE-ID ::= 396
id-PosMeasurementResultList							ProtocolIE-ID ::= 397
id-TRPInformationTypeListTRPReq						ProtocolIE-ID ::= 398
id-TRPInformationTypeItem							ProtocolIE-ID ::= 399
id-TRPInformationListTRPResp						ProtocolIE-ID ::= 400
id-TRPInformationItem								ProtocolIE-ID ::= 401
id-LMF-MeasurementID								ProtocolIE-ID ::= 402
id-SRSType									ProtocolIE-ID ::= 403
id-ActivationTime								ProtocolIE-ID ::= 404
id-AbortTransmission								ProtocolIE-ID ::= 405
id-PositioningBroadcastCells							ProtocolIE-ID ::= 406
id-SRSConfiguration								ProtocolIE-ID ::= 407
id-PosReportCharacteristics							ProtocolIE-ID ::= 408
id-PosMeasurementPeriodicity							ProtocolIE-ID ::= 409
id-TRPList									ProtocolIE-ID ::= 410
id-RAN-MeasurementID								ProtocolIE-ID ::= 411
id-LMF-UE-MeasurementID								ProtocolIE-ID ::= 412
id-RAN-UE-MeasurementID								ProtocolIE-ID ::= 413
id-E-CID-MeasurementQuantities							ProtocolIE-ID ::= 414
id-E-CID-MeasurementQuantities-Item						ProtocolIE-ID ::= 415
id-E-CID-MeasurementPeriodicity							ProtocolIE-ID ::= 416
id-E-CID-MeasurementResult							ProtocolIE-ID ::= 417
id-Cell-Portion-ID								ProtocolIE-ID ::= 418
id-SFNInitialisationTime							ProtocolIE-ID ::= 419
id-SystemFrameNumber								ProtocolIE-ID ::= 420
id-SlotNumber									ProtocolIE-ID ::= 421
id-TRP-MeasurementRequestList							ProtocolIE-ID ::= 422
id-MeasurementBeamInfoRequest							ProtocolIE-ID ::= 423
id-E-CID-ReportCharacteristics							ProtocolIE-ID ::= 424
id-ConfiguredTACIndication							ProtocolIE-ID ::= 425
id-Extended-GNB-DU-Name								ProtocolIE-ID ::= 426
id-Extended-GNB-CU-Name								ProtocolIE-ID ::= 427


END
