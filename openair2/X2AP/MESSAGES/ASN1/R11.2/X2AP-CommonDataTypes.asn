X2AP-CommonDataTypes {
itu-t (0) identified-organization (4) etsi (0) mobileDomain (0) 
eps-Access (21) modules (3) x2ap (2) version1 (1) x2ap-CommonDataTypes (3)  }

DEFINITIONS AUTOMATIC TAGS ::= 

BEGIN

-- **************************************************************
--
-- Extension constants
--
-- **************************************************************

x2ap-maxPrivateIEs 									INTEGER ::= 65535
x2ap-maxProtocolExtensions 							INTEGER ::= 65535
x2ap-maxProtocolIEs									INTEGER ::= 65535

-- **************************************************************
--
-- Common Data Types
--
-- **************************************************************

X2ap-Criticality		::= ENUMERATED { reject, ignore, notify }

X2ap-Presence		::= ENUMERATED { optional, conditional, mandatory }

X2ap-PrivateIE-ID	::= CHOICE {
	local				INTEGER (0.. x2ap-maxPrivateIEs),
	global				OBJECT IDENTIFIER
}

--X2ap-ProcedureCode		::= INTEGER (0..255)
X2ap-ProcedureCode       ::= INTEGER {
    id-handoverPreparation                                          (0),
    id-handoverCancel                                               (1),
    id-loadIndication                                               (2),
    id-errorIndication                                              (3),
    id-snStatusTransfer                                             (4),
    id-uEContextRelease                                             (5),
    id-x2Setup                                                      (6),
    id-reset                                                        (7),
    id-eNBConfigurationUpdate                                       (8),
    id-resourceStatusReportingInitiation                            (9),
    id-resourceStatusReporting                                      (10),
    id-privateMessage                                               (11),
    id-mobilitySettingsChange                                       (12),
    id-rLFIndication                                                (13),
    id-handoverReport                                               (14),
    id-cellActivation                                               (15)
} (0..255)

--X2ap-ProtocolIE-ID		::= INTEGER (0..x2ap-maxProtocolIEs)
X2ap-ProtocolIE-ID       ::= INTEGER {
    id-E-RABs-Admitted-Item                                                     (0),
    id-E-RABs-Admitted-List                                                     (1),
    id-E-RAB-Item                                                               (2),
    id-E-RABs-NotAdmitted-List                                                  (3),
    id-E-RABs-ToBeSetup-Item                                                    (4),
    id-Cause                                                                    (5),
    id-CellInformation                                                          (6),
    id-CellInformation-Item                                                     (7),
    id-New-eNB-UE-X2AP-ID                                                       (9),
    id-Old-eNB-UE-X2AP-ID                                                       (10),
    id-TargetCell-ID                                                            (11),
    id-TargeteNBtoSource-eNBTransparentContainer                                (12),
    id-TraceActivation                                                          (13),
    id-UE-ContextInformation                                                    (14),
    id-UE-HistoryInformation                                                    (15),
    id-UE-X2AP-ID                                                               (16),
    id-CriticalityDiagnostics                                                   (17),
    id-E-RABs-SubjectToStatusTransfer-List                                      (18),
    id-E-RABs-SubjectToStatusTransfer-Item                                      (19),
    id-ServedCells                                                              (20),
    id-GlobalENB-ID                                                             (21),
    id-TimeToWait                                                               (22),
    id-GUMMEI-ID                                                                (23),
    id-GUGroupIDList                                                            (24),
    id-ServedCellsToAdd                                                         (25),
    id-ServedCellsToModify                                                      (26),
    id-ServedCellsToDelete                                                      (27),
    id-Registration-Request                                                     (28),
    id-CellToReport                                                             (29),
    id-ReportingPeriodicity                                                     (30),
    id-CellToReport-Item                                                        (31),
    id-CellMeasurementResult                                                    (32),
    id-CellMeasurementResult-Item                                               (33),
    id-GUGroupIDToAddList                                                       (34),
    id-GUGroupIDToDeleteList                                                    (35),
    id-SRVCCOperationPossible                                                   (36),
    id-Measurement-ID                                                           (37),
    id-ReportCharacteristics                                                    (38),
    id-ENB1-Measurement-ID                                                      (39),
    id-ENB2-Measurement-ID                                                      (40),
    id-Number-of-Antennaports                                                   (41),
    id-CompositeAvailableCapacityGroup                                          (42),
    id-ENB1-Cell-ID                                                             (43),
    id-ENB2-Cell-ID                                                             (44),
    id-ENB2-Proposed-Mobility-Parameters                                        (45),
    id-ENB1-Mobility-Parameters                                                 (46),
    id-ENB2-Mobility-Parameters-Modification-Range                              (47),
    id-FailureCellPCI                                                           (48),
    id-Re-establishmentCellECGI                                                 (49),
    id-FailureCellCRNTI                                                         (50),
    id-ShortMAC-I                                                               (51),
    id-SourceCellECGI                                                           (52),
    id-FailureCellECGI                                                          (53),
    id-HandoverReportType                                                       (54),
    id-PRACH-Configuration                                                      (55),
    id-MBSFN-Subframe-Info                                                      (56),
    id-ServedCellsToActivate                                                    (57),
    id-ActivatedCellList                                                        (58),
    id-DeactivationIndication                                                   (59),
    id-UE-RLF-Report-Container                                                  (60),
    id-ABSInformation								(61),
    id-InvokeIndication								(62),
    id-ABS-Status								(63),
    id-PartialSuccessIndicator							(64),
    id-MeasurementInitiationResult-List						(65),
    id-MeasurementInitiationResult-Item						(66),
    id-MeasurementFailureCause-Item						(67),
    id-CompleteFailureCauseInformation-List					(68),
    id-CompleteFailureCauseInformation-Item					(69),
    id-CSG-Id									(70),
    id-CSGMembershipStatus							(71),
    id-MDTConfiguration								(72),
    id-ManagementBasedMDTallowed						(74),
    id-RRCConnSetupIndicator							(75),	
    id-NeighbourTAC								(76),
    id-Time-UE-StayedInCell-EnhancedGranularity					(77),	
    id-RRCConnReestabIndicator							(78),	
    id-MBMS-Service-Area-List							(79),
    id-HO-cause									(80),
    id-TargetCellInUTRAN							(81),
    id-MultibandInfoList							(84)
} (0..x2ap-maxProtocolIEs)


X2ap-TriggeringMessage	::= ENUMERATED { initiating-message, successful-outcome, unsuccessful-outcome}

END
