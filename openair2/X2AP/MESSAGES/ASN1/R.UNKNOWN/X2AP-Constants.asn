-- **************************************************************
--
-- Constant definitions
--
-- **************************************************************

X2AP-Constants {
itu-t (0) identified-organization (4) etsi (0) mobileDomain (0)
eps-Access (21) modules (3) x2ap (2) version1 (1) x2ap-Constants (4) }

DEFINITIONS AUTOMATIC TAGS ::=

BEGIN

IMPORTS
    ProcedureCode,
    ProtocolIE-ID
FROM X2AP-CommonDataTypes;

-- **************************************************************
--
-- Elementary Procedures
--
-- **************************************************************

id-handoverPreparation                                          ProcedureCode ::= 0
id-handoverCancel                                               ProcedureCode ::= 1
id-loadIndication                                               ProcedureCode ::= 2
id-errorIndication                                              ProcedureCode ::= 3
id-snStatusTransfer                                             ProcedureCode ::= 4
id-uEContextRelease                                             ProcedureCode ::= 5
id-x2Setup                                                      ProcedureCode ::= 6
id-reset                                                        ProcedureCode ::= 7
id-eNBConfigurationUpdate                                       ProcedureCode ::= 8
id-resourceStatusReportingInitiation                            ProcedureCode ::= 9
id-resourceStatusReporting                                      ProcedureCode ::= 10
id-privateMessage                                               ProcedureCode ::= 11
id-mobilitySettingsChange                                       ProcedureCode ::= 12
id-rLFIndication                                                ProcedureCode ::= 13
id-handoverReport                                               ProcedureCode ::= 14
id-cellActivation                                               ProcedureCode ::= 15



-- **************************************************************
--
-- Lists
--
-- **************************************************************

maxEARFCN                                   INTEGER ::= 65535
maxInterfaces                               INTEGER ::= 16
maxCellineNB                                INTEGER ::= 256
maxnoofBearers                              INTEGER ::= 256
maxNrOfErrors                               INTEGER ::= 256
maxnoofPDCP-SN                              INTEGER ::= 16      -- FFS Value to be checked
maxnoofEPLMNs                               INTEGER ::= 15
maxnoofEPLMNsPlusOne                        INTEGER ::= 16
maxnoofForbLACs                             INTEGER ::= 4096
maxnoofForbTACs                             INTEGER ::= 4096
maxnoofBPLMNs                               INTEGER ::= 6
maxnoofNeighbours                           INTEGER ::= 512
maxnoofPRBs                                 INTEGER ::= 110
maxPools                                    INTEGER ::= 16
maxnoofCells                                INTEGER ::= 16
maxnoofMBSFN                                INTEGER ::= 8




-- **************************************************************
--
-- IEs
--
-- **************************************************************

id-E-RABs-Admitted-Item                                                     ProtocolIE-ID ::= 0
id-E-RABs-Admitted-List                                                     ProtocolIE-ID ::= 1
id-E-RAB-Item                                                               ProtocolIE-ID ::= 2
id-E-RABs-NotAdmitted-List                                                  ProtocolIE-ID ::= 3
id-E-RABs-ToBeSetup-Item                                                    ProtocolIE-ID ::= 4
id-Cause                                                                    ProtocolIE-ID ::= 5
id-CellInformation                                                          ProtocolIE-ID ::= 6
id-CellInformation-Item                                                     ProtocolIE-ID ::= 7
id-New-eNB-UE-X2AP-ID                                                       ProtocolIE-ID ::= 9
id-Old-eNB-UE-X2AP-ID                                                       ProtocolIE-ID ::= 10
id-TargetCell-ID                                                            ProtocolIE-ID ::= 11
id-TargeteNBtoSource-eNBTransparentContainer                                ProtocolIE-ID ::= 12
id-TraceActivation                                                          ProtocolIE-ID ::= 13
id-UE-ContextInformation                                                    ProtocolIE-ID ::= 14
id-UE-HistoryInformation                                                    ProtocolIE-ID ::= 15
id-UE-X2AP-ID                                                               ProtocolIE-ID ::= 16
id-CriticalityDiagnostics                                                   ProtocolIE-ID ::= 17
id-E-RABs-SubjectToStatusTransfer-List                                      ProtocolIE-ID ::= 18
id-E-RABs-SubjectToStatusTransfer-Item                                      ProtocolIE-ID ::= 19
id-ServedCells                                                              ProtocolIE-ID ::= 20
id-GlobalENB-ID                                                             ProtocolIE-ID ::= 21
id-TimeToWait                                                               ProtocolIE-ID ::= 22
id-GUMMEI-ID                                                                ProtocolIE-ID ::= 23
id-GUGroupIDList                                                            ProtocolIE-ID ::= 24
id-ServedCellsToAdd                                                         ProtocolIE-ID ::= 25
id-ServedCellsToModify                                                      ProtocolIE-ID ::= 26
id-ServedCellsToDelete                                                      ProtocolIE-ID ::= 27
id-Registration-Request                                                     ProtocolIE-ID ::= 28
id-CellToReport                                                             ProtocolIE-ID ::= 29
id-ReportingPeriodicity                                                     ProtocolIE-ID ::= 30
id-CellToReport-Item                                                        ProtocolIE-ID ::= 31
id-CellMeasurementResult                                                    ProtocolIE-ID ::= 32
id-CellMeasurementResult-Item                                               ProtocolIE-ID ::= 33
id-GUGroupIDToAddList                                                       ProtocolIE-ID ::= 34
id-GUGroupIDToDeleteList                                                    ProtocolIE-ID ::= 35
id-SRVCCOperationPossible                                                   ProtocolIE-ID ::= 36
id-Measurement-ID                                                           ProtocolIE-ID ::= 37
id-ReportCharacteristics                                                    ProtocolIE-ID ::= 38
id-ENB1-Measurement-ID                                                      ProtocolIE-ID ::= 39
id-ENB2-Measurement-ID                                                      ProtocolIE-ID ::= 40
id-Number-of-Antennaports                                                   ProtocolIE-ID ::= 41
id-CompositeAvailableCapacityGroup                                          ProtocolIE-ID ::= 42
id-ENB1-Cell-ID                                                             ProtocolIE-ID ::= 43
id-ENB2-Cell-ID                                                             ProtocolIE-ID ::= 44
id-ENB2-Proposed-Mobility-Parameters                                        ProtocolIE-ID ::= 45
id-ENB1-Mobility-Parameters                                                 ProtocolIE-ID ::= 46
id-ENB2-Mobility-Parameters-Modification-Range                              ProtocolIE-ID ::= 47
id-FailureCellPCI                                                           ProtocolIE-ID ::= 48
id-Re-establishmentCellECGI                                                 ProtocolIE-ID ::= 49
id-FailureCellCRNTI                                                         ProtocolIE-ID ::= 50
id-ShortMAC-I                                                               ProtocolIE-ID ::= 51
id-SourceCellECGI                                                           ProtocolIE-ID ::= 52
id-FailureCellECGI                                                          ProtocolIE-ID ::= 53
id-HandoverReportType                                                       ProtocolIE-ID ::= 54
id-PRACH-Configuration                                                      ProtocolIE-ID ::= 55
id-MBSFN-Subframe-Info                                                      ProtocolIE-ID ::= 56
id-ServedCellsToActivate                                                    ProtocolIE-ID ::= 57
id-ActivatedCellList                                                        ProtocolIE-ID ::= 58
id-DeactivationIndication                                                   ProtocolIE-ID ::= 59
id-UE-RLF-Report-Container                                                  ProtocolIE-ID ::= 60

END
