-- **************************************************************
--
-- Information Element Definitions
--
-- **************************************************************

X2AP-IEs {
itu-t (0) identified-organization (4) etsi (0) mobileDomain (0)
eps-Access (21) modules (3) x2ap (2) version1 (1) x2ap-IEs (2) }

DEFINITIONS AUTOMATIC TAGS ::=

BEGIN

IMPORTS

    id-E-RAB-Item,
    id-Number-of-Antennaports,
    id-MBSFN-Subframe-Info,
    id-PRACH-Configuration,

    maxnoofBearers,
    maxCellineNB,
    maxEARFCN,
    maxInterfaces,

    maxnoofBPLMNs,
    maxnoofCells,
    maxnoofEPLMNs,
    maxnoofEPLMNsPlusOne,
    maxnoofForbLACs,
    maxnoofForbTACs,
    maxnoofNeighbours,
    maxnoofPRBs,
    maxNrOfErrors,
    maxPools,
    maxnoofMBSFN

FROM X2AP-Constants

    Criticality,
    ProcedureCode,
    ProtocolIE-ID,
    TriggeringMessage,
    maxProtocolExtensions

FROM X2AP-CommonDataTypes

    IE
FROM X2AP-PDU;

IE-Extensions ::= SEQUENCE (SIZE (1..maxProtocolExtensions)) OF IE

-- A

AS-SecurityInformation ::= SEQUENCE {
    key-eNodeB-star     Key-eNodeB-Star,
    nextHopChainingCount            NextHopChainingCount,
    -- iE-Extensions                       ProtocolExtensionContainer { { AS-SecurityInformation-ExtIEs} } OPTIONAL,
    iE-Extensions               IE-Extensions OPTIONAL,
    ...
}

AllocationAndRetentionPriority ::= SEQUENCE {
    priorityLevel               PriorityLevel,
    pre-emptionCapability       Pre-emptionCapability,
    pre-emptionVulnerability    Pre-emptionVulnerability,
    -- iE-Extensions               ProtocolExtensionContainer { {AllocationAndRetentionPriority-ExtIEs} } OPTIONAL,
    iE-Extensions               IE-Extensions OPTIONAL,
    ...
}

ActivatedCellList ::= SEQUENCE (SIZE (1..maxCellineNB)) OF ActivatedCellList-Item

ActivatedCellList-Item::= SEQUENCE {
    ecgi                                ECGI,
    -- iE-Extensions                       ProtocolExtensionContainer { { ActivatedCellList-Item-ExtIEs} } OPTIONAL,
    iE-Extensions               IE-Extensions OPTIONAL,
    ...
}

-- B


BitRate ::= INTEGER (0..10000000000)
BroadcastPLMNs-Item ::= SEQUENCE (SIZE(1..maxnoofBPLMNs)) OF PLMN-Identity


-- C

CapacityValue ::= INTEGER (0..100)

CellCapacityClassValue ::= INTEGER (1..100, ...)

CellToReport-List       ::= SEQUENCE (SIZE (1..maxCellineNB)) OF IE

CellToReport-Item ::= SEQUENCE {
    cell-ID                                 ECGI,
    -- iE-Extensions                           ProtocolExtensionContainer { {CellToReport-Item-ExtIEs} } OPTIONAL,
    iE-Extensions               IE-Extensions OPTIONAL,
    ...
}

CellMeasurementResult-List      ::= SEQUENCE (SIZE (1..maxCellineNB)) OF IE

CellMeasurementResult-Item ::= SEQUENCE {
    cell-ID                         ECGI,
    hWOverLoadIndicator             HWLoadIndicator     OPTIONAL,
    s1TNLOverLoadIndicator          S1TNLLoadIndicator  OPTIONAL,
    radioResourceStatus             RadioResourceStatus OPTIONAL,
    -- iE-Extensions                   ProtocolExtensionContainer { {CellMeasurementResult-Item-ExtIEs} }  OPTIONAL,
    iE-Extensions               IE-Extensions OPTIONAL,
    ...
}

ReportingPeriodicity ::= ENUMERATED {
    one-thousand-ms,
    two-thousand-ms,
    five-thousand-ms,
    ten-thousand-ms,
    ...
}

Cause ::= CHOICE {
    radioNetwork        CauseRadioNetwork,
    transport           CauseTransport,
    protocol            CauseProtocol,
    misc                CauseMisc,
    ...
}

CauseMisc ::= ENUMERATED {
    control-processing-overload,
    hardware-failure,
    om-intervention,
    not-enough-user-plane-processing-resources,
    unspecified,
    ...
}

CauseProtocol ::= ENUMERATED {
    transfer-syntax-error,
    abstract-syntax-error-reject,
    abstract-syntax-error-ignore-and-notify,
    message-not-compatible-with-receiver-state,
    semantic-error,
    unspecified,
    abstract-syntax-error-falsely-constructed-message,
    ...
}

CauseRadioNetwork ::= ENUMERATED {
    handover-desirable-for-radio-reasons,
    time-critical-handover,
    resource-optimisation-handover,
    reduce-load-in-serving-cell,
    partial-handover,
    unknown-new-eNB-UE-X2AP-ID,
    unknown-old-eNB-UE-X2AP-ID,
    unknown-pair-of-UE-X2AP-ID,
    ho-target-not-allowed,
    tx2relocoverall-expiry,
    trelocprep-expiry,
    cell-not-available,
    no-radio-resources-available-in-target-cell,
    invalid-MME-GroupID,
    unknown-MME-Code,
    encryption-and-or-integrity-protection-algorithms-not-supported,
    reportCharacteristicsEmpty,
    noReportPeriodicity,
    existingMeasurementID,
    unknown-eNB-Measurement-ID,
    measurement-temporarily-not-available,
    unspecified,
    ...,
    load-balancing,
    handover-optimisation,
    value-out-of-allowed-range,
    multiple-E-RAB-ID-instances,
    switch-off-ongoing,
    not-supported-QCI-value

}

CauseTransport ::= ENUMERATED {
    transport-resource-unavailable,
    unspecified,
    ...
}

Cell-Size ::= ENUMERATED {verysmall, small, medium, large, ... }

CellInformation-List        ::= SEQUENCE (SIZE (1..maxCellineNB)) OF IE

CellInformation-Item ::= SEQUENCE {
    cell-ID                         ECGI,
    ul-InterferenceOverloadIndication       UL-InterferenceOverloadIndication       OPTIONAL,
    ul-HighInterferenceIndicationInfo       UL-HighInterferenceIndicationInfo       OPTIONAL,
    relativeNarrowbandTxPower               RelativeNarrowbandTxPower               OPTIONAL,
    -- iE-Extensions                           ProtocolExtensionContainer { {CellInformation-Item-ExtIEs} }    OPTIONAL,
    iE-Extensions               IE-Extensions OPTIONAL,
    ...
}

CellType ::= SEQUENCE {
    cell-Size                       Cell-Size,
    -- iE-Extensions                   ProtocolExtensionContainer { { CellType-ExtIEs}}    OPTIONAL,
    iE-Extensions               IE-Extensions OPTIONAL,
    ...
}

CompositeAvailableCapacityGroup ::= SEQUENCE {
    dL-CompositeAvailableCapacity                   CompositeAvailableCapacity,
    uL-CompositeAvailableCapacity                   CompositeAvailableCapacity,
    -- iE-Extensions                                   ProtocolExtensionContainer { { CompositeAvailableCapacityGroup-ExtIEs} } OPTIONAL,
    iE-Extensions               IE-Extensions OPTIONAL,
    ...
}

CompositeAvailableCapacity ::= SEQUENCE {
    cellCapacityClassValue                          CellCapacityClassValue              OPTIONAL,
    capacityValue                                   CapacityValue,
    -- iE-Extensions                                   ProtocolExtensionContainer { { CompositeAvailableCapacity-ExtIEs} } OPTIONAL,
    iE-Extensions               IE-Extensions OPTIONAL,
    ...
}

COUNTvalue ::= SEQUENCE {
    pDCP-SN                 PDCP-SN,
    hFN                     HFN,
    -- iE-Extensions           ProtocolExtensionContainer { { COUNTvalue-ExtIEs} } OPTIONAL,
    iE-Extensions               IE-Extensions OPTIONAL,
    ...
}

CriticalityDiagnostics ::= SEQUENCE {
    procedureCode                   ProcedureCode                   OPTIONAL,
    triggeringMessage               TriggeringMessage               OPTIONAL,
    procedureCriticality            Criticality                     OPTIONAL,
    iEsCriticalityDiagnostics       CriticalityDiagnostics-IE-List  OPTIONAL,
    -- iE-Extensions                   ProtocolExtensionContainer { {CriticalityDiagnostics-ExtIEs} }  OPTIONAL,
    iE-Extensions               IE-Extensions OPTIONAL,
    ...
}

CriticalityDiagnostics-IE-List ::= SEQUENCE (SIZE (1..maxNrOfErrors)) OF CriticalityDiagnostics-IE-Elm

CriticalityDiagnostics-IE-Elm ::= SEQUENCE {
    iECriticality           Criticality,
    iE-ID                   ProtocolIE-ID,
    typeOfError             TypeOfError,
    -- iE-Extensions           ProtocolExtensionContainer { {CriticalityDiagnostics-IE-List-ExtIEs} } OPTIONAL,
    iE-Extensions               IE-Extensions OPTIONAL,
    ...
}

CRNTI ::= BIT STRING (SIZE (16))

CyclicPrefixDL ::= ENUMERATED {
    normal,
    extended,
    ...
}

CyclicPrefixUL ::= ENUMERATED {
    normal,
    extended,
    ...
}


-- D

DeactivationIndication::= ENUMERATED {
    deactivated,
    ...
}

DL-Forwarding ::= ENUMERATED {
    dL-forwardingProposed,
    ...
}

-- E

E-RABs-Admitted-List        ::= SEQUENCE (SIZE (1..maxnoofBearers)) OF IE

E-RABs-Admitted-Item ::= SEQUENCE {
    e-RAB-ID                    E-RAB-ID,
    uL-GTP-TunnelEndpoint           GTPtunnelEndpoint   OPTIONAL,
    dL-GTP-TunnelEndpoint           GTPtunnelEndpoint   OPTIONAL,
    -- iE-Extensions                   ProtocolExtensionContainer { {E-RABs-Admitted-Item-ExtIEs} }    OPTIONAL,
    iE-Extensions               IE-Extensions OPTIONAL,
    ...
}

E-RABs-ToBeSetup-List ::= SEQUENCE (SIZE(1..maxnoofBearers)) OF IE

E-RABs-ToBeSetup-Item ::= SEQUENCE {
    e-RAB-ID                        E-RAB-ID,
    e-RAB-Level-QoS-Parameters      E-RAB-Level-QoS-Parameters,
    dL-Forwarding                   DL-Forwarding                                                   OPTIONAL,
    uL-GTPtunnelEndpoint            GTPtunnelEndpoint,
    -- iE-Extensions                   ProtocolExtensionContainer { {E-RABs-ToBeSetup-ItemExtIEs} } OPTIONAL,
    iE-Extensions               IE-Extensions OPTIONAL,
    ...
}

E-RABs-SubjectToStatusTransfer-List ::= SEQUENCE (SIZE (1..maxnoofBearers)) OF IE

E-RABs-SubjectToStatusTransfer-Item ::= SEQUENCE {
    e-RAB-ID                                E-RAB-ID,
    receiveStatusofULPDCPSDUs               ReceiveStatusofULPDCPSDUs           OPTIONAL,
    uL-COUNTvalue                   COUNTvalue,
    dL-COUNTvalue                   COUNTvalue,
    -- iE-Extensions                           ProtocolExtensionContainer { {E-RABs-SubjectToStatusTransfer-ItemExtIEs} } OPTIONAL,
    iE-Extensions               IE-Extensions OPTIONAL,
    ...
}

EARFCN ::= INTEGER (0..maxEARFCN)

FDD-Info ::= SEQUENCE {
    uL-EARFCN                       EARFCN,
    dL-EARFCN                       EARFCN,
    uL-Transmission-Bandwidth       Transmission-Bandwidth,
    dL-Transmission-Bandwidth       Transmission-Bandwidth,
    -- iE-Extensions               ProtocolExtensionContainer { {FDD-Info-ExtIEs} } OPTIONAL,
    iE-Extensions               IE-Extensions OPTIONAL,
    ...
}

TDD-Info ::= SEQUENCE {
    eARFCN                          EARFCN,
    transmission-Bandwidth          Transmission-Bandwidth,
    subframeAssignment              SubframeAssignment,
    specialSubframe-Info                SpecialSubframe-Info,
    -- iE-Extensions               ProtocolExtensionContainer { {TDD-Info-ExtIEs} } OPTIONAL,
    iE-Extensions               IE-Extensions OPTIONAL,
    ...
}

EUTRA-Mode-Info ::= CHOICE {
    fDD     FDD-Info,
    tDD     TDD-Info,
    ...
}

ECGI ::= SEQUENCE {
    pLMN-Identity               PLMN-Identity,
    eUTRANcellIdentifier        EUTRANCellIdentifier,
    -- iE-Extensions               ProtocolExtensionContainer { {ECGI-ExtIEs} } OPTIONAL,
    iE-Extensions               IE-Extensions OPTIONAL,
    ...
}

ENB-ID ::= CHOICE {
    macro-eNB-ID    BIT STRING (SIZE (20)),
    home-eNB-ID     BIT STRING (SIZE (28)),
    ...
}

EncryptionAlgorithms ::= BIT STRING (SIZE (16, ...))

EPLMNs ::= SEQUENCE (SIZE(1..maxnoofEPLMNs)) OF PLMN-Identity

E-RAB-ID ::= INTEGER (0..15, ...)

E-RAB-Level-QoS-Parameters ::= SEQUENCE {
    qCI                             QCI,
    allocationAndRetentionPriority  AllocationAndRetentionPriority,
    gbrQosInformation               GBR-QosInformation                                                  OPTIONAL,
    -- iE-Extensions                   ProtocolExtensionContainer { { E-RAB-Level-QoS-Parameters-ExtIEs} } OPTIONAL,
    iE-Extensions               IE-Extensions OPTIONAL,
    ...
}

E-RAB-List ::= SEQUENCE (SIZE(1.. maxnoofBearers)) OF IE

E-RAB-Item ::= SEQUENCE {
    e-RAB-ID                E-RAB-ID,
    cause                       Cause,
    -- iE-Extensions               ProtocolExtensionContainer { {E-RAB-Item-ExtIEs} } OPTIONAL,
    iE-Extensions               IE-Extensions OPTIONAL,
    ...
}

EUTRANCellIdentifier ::= BIT STRING (SIZE (28))

EUTRANTraceID       ::= OCTET STRING (SIZE (8))


EventType ::= ENUMERATED{
    change-of-serving-cell,
    ...
}


-- F

ForbiddenInterRATs ::= ENUMERATED {
    all,
    geran,
    utran,
    cdma2000,
    ...,
    geranandutran,
    cdma2000andutran

}

ForbiddenTAs ::= SEQUENCE (SIZE(1.. maxnoofEPLMNsPlusOne)) OF ForbiddenTAs-Item

ForbiddenTAs-Item ::= SEQUENCE {
    pLMN-Identity       PLMN-Identity,
    forbiddenTACs       ForbiddenTACs,
    -- iE-Extensions       ProtocolExtensionContainer { {ForbiddenTAs-Item-ExtIEs} } OPTIONAL,
    iE-Extensions               IE-Extensions OPTIONAL,
    ...
}

ForbiddenTACs ::= SEQUENCE (SIZE(1..maxnoofForbTACs)) OF TAC

ForbiddenLAs ::= SEQUENCE (SIZE(1..maxnoofEPLMNsPlusOne)) OF ForbiddenLAs-Item

ForbiddenLAs-Item ::= SEQUENCE {
    pLMN-Identity       PLMN-Identity,
    forbiddenLACs       ForbiddenLACs,
    -- iE-Extensions       ProtocolExtensionContainer { {ForbiddenLAs-Item-ExtIEs} } OPTIONAL,
    iE-Extensions               IE-Extensions OPTIONAL,
    ...
}

ForbiddenLACs ::= SEQUENCE (SIZE(1..maxnoofForbLACs)) OF LAC

Fourframes ::= BIT STRING (SIZE (24))

-- G

GBR-QosInformation ::= SEQUENCE {
    e-RAB-MaximumBitrateDL          BitRate,
    e-RAB-MaximumBitrateUL          BitRate,
    e-RAB-GuaranteedBitrateDL       BitRate,
    e-RAB-GuaranteedBitrateUL       BitRate,
    -- iE-Extensions                   ProtocolExtensionContainer { { GBR-QosInformation-ExtIEs} } OPTIONAL,
    iE-Extensions               IE-Extensions OPTIONAL,
    ...
}

GlobalENB-ID ::= SEQUENCE {
    pLMN-Identity           PLMN-Identity,
    eNB-ID                  ENB-ID,
    -- iE-Extensions           ProtocolExtensionContainer { {GlobalENB-ID-ExtIEs} } OPTIONAL,
    iE-Extensions               IE-Extensions OPTIONAL,
    ...
}

GTPtunnelEndpoint ::= SEQUENCE {
    transportLayerAddress           TransportLayerAddress,
    gTP-TEID                        GTP-TEI,
    -- iE-Extensions                   ProtocolExtensionContainer { {GTPtunnelEndpoint-ExtIEs} } OPTIONAL,
    iE-Extensions               IE-Extensions OPTIONAL,
    ...
}

GTP-TEI                 ::= OCTET STRING (SIZE (4))

GUGroupIDList       ::= SEQUENCE (SIZE (1..maxPools)) OF GU-Group-ID


GU-Group-ID         ::= SEQUENCE {
    pLMN-Identity       PLMN-Identity,
    mME-Group-ID        MME-Group-ID,
    -- iE-Extensions       ProtocolExtensionContainer { {GU-Group-ID-ExtIEs} } OPTIONAL,
    iE-Extensions               IE-Extensions OPTIONAL,
    ...
}

GUMMEI          ::= SEQUENCE {

    gU-Group-ID     GU-Group-ID,
    mME-Code            MME-Code,
    -- iE-Extensions                   ProtocolExtensionContainer { {GUMMEI-ExtIEs} } OPTIONAL,
    iE-Extensions               IE-Extensions OPTIONAL,
    ...
}

-- H

HandoverReportType  ::= ENUMERATED {
    hoTooEarly,
    hoToWrongCell,
    ...
}

HandoverRestrictionList ::= SEQUENCE {
    servingPLMN                 PLMN-Identity,
    equivalentPLMNs             EPLMNs                  OPTIONAL,
    forbiddenTAs                ForbiddenTAs            OPTIONAL,
    forbiddenLAs                ForbiddenLAs            OPTIONAL,
    forbiddenInterRATs          ForbiddenInterRATs      OPTIONAL,
    -- iE-Extensions               ProtocolExtensionContainer { {HandoverRestrictionList-ExtIEs} } OPTIONAL,
    iE-Extensions               IE-Extensions OPTIONAL,
    ...
}

HFN ::= INTEGER (0..1048575)

HWLoadIndicator ::= SEQUENCE {
    dLHWLoadIndicator           LoadIndicator,
    uLHWLoadIndicator           LoadIndicator,
    -- iE-Extensions               ProtocolExtensionContainer { { HWLoadIndicator-ExtIEs} } OPTIONAL,
    iE-Extensions               IE-Extensions OPTIONAL,
    ...
}

-- I

IntegrityProtectionAlgorithms ::= BIT STRING (SIZE (16, ...))

InterfacesToTrace ::= BIT STRING (SIZE (8))
-- J
-- K


Key-eNodeB-Star  ::= BIT STRING (SIZE(256))

-- L


LAC                 ::= OCTET STRING (SIZE (2)) --(EXCEPT ('0000'H|'FFFE'H))

LastVisitedCell-Item ::= CHOICE {
    e-UTRAN-Cell                    LastVisitedEUTRANCellInformation,
    uTRAN-Cell                      LastVisitedUTRANCellInformation,
    gERAN-Cell                      LastVisitedGERANCellInformation,
    ...
}

LastVisitedEUTRANCellInformation ::= SEQUENCE {
    global-Cell-ID                  ECGI,
    cellType                        CellType,
    time-UE-StayedInCell            Time-UE-StayedInCell,
    -- iE-Extensions                   ProtocolExtensionContainer { { LastVisitedEUTRANCellInformation-ExtIEs} } OPTIONAL,
    iE-Extensions               IE-Extensions OPTIONAL,
    ...
}

LastVisitedUTRANCellInformation ::= OCTET STRING

LastVisitedGERANCellInformation ::= CHOICE {
    undefined                       NULL,
    ...
}


LoadIndicator ::= ENUMERATED {
    lowLoad,
    mediumLoad,
    highLoad,
    overLoad,
    ...
}



LocationReportingInformation ::= SEQUENCE {
    eventType       EventType,
    reportArea      ReportArea,
    -- iE-Extensions       ProtocolExtensionContainer { {LocationReportingInformation-ExtIEs} } OPTIONAL,
    iE-Extensions               IE-Extensions OPTIONAL,
    ...
}

-- M


MME-Group-ID    ::= OCTET STRING (SIZE (2))

MME-Code        ::= OCTET STRING (SIZE (1))

Measurement-ID  ::= INTEGER (1..4095, ...)

MBSFN-Subframe-Infolist::= SEQUENCE (SIZE(1.. maxnoofMBSFN)) OF MBSFN-Subframe-Info

MBSFN-Subframe-Info ::= SEQUENCE {
    radioframeAllocationPeriod      RadioframeAllocationPeriod,
    radioframeAllocationOffset      RadioframeAllocationOffset,
    subframeAllocation              SubframeAllocation,
    -- iE-Extensions           ProtocolExtensionContainer { { MBSFN-Subframe-Info-ExtIEs } }   OPTIONAL,
    iE-Extensions               IE-Extensions OPTIONAL,
    ...
}

MobilityParametersModificationRange ::= SEQUENCE {
    handoverTriggerChangeLowerLimit     INTEGER (-20..20),
    handoverTriggerChangeUpperLimit     INTEGER (-20..20),
    ...
}

MobilityParametersInformation ::= SEQUENCE {
    handoverTriggerChange           INTEGER (-20..20),
    ...
}


-- N

Neighbour-Information ::= SEQUENCE (SIZE (0..maxnoofNeighbours)) OF Neighbour-Information-Elm

Neighbour-Information-Elm ::= SEQUENCE {
    eCGI                        ECGI,
    pCI                     PCI,
    eARFCN                      EARFCN,
    -- iE-Extensions        ProtocolExtensionContainer { {Neighbour-Information-ExtIEs} } OPTIONAL,
    iE-Extensions               IE-Extensions OPTIONAL,
    ...
}

NextHopChainingCount ::= INTEGER (0..7)

Number-of-Antennaports ::= ENUMERATED {
        an1,
        an2,
        an4,
        ...
}

-- O

Oneframe ::= BIT STRING (SIZE (6))

-- P

PDCP-SN ::= INTEGER (0..4095)

PCI ::= INTEGER (0..503, ...)


PLMN-Identity ::= OCTET STRING (SIZE(3))

PRACH-Configuration  ::= SEQUENCE {
    rootSequenceIndex                       INTEGER (0..837),
    zeroCorrelationIndex                    INTEGER (0..15),
    highSpeedFlag                           BOOLEAN,
    prach-FreqOffset                        INTEGER (0..94),
    prach-ConfigIndex                       INTEGER (0..63)        OPTIONAL,  -- present for TDD --
    -- iE-Extensions                           ProtocolExtensionContainer { {PRACH-Configuration-ExtIEs} } OPTIONAL,
    iE-Extensions               IE-Extensions OPTIONAL,
    ...
}

Pre-emptionCapability ::= ENUMERATED {
    shall-not-trigger-pre-emption,
    may-trigger-pre-emption
}

Pre-emptionVulnerability ::= ENUMERATED {
    not-pre-emptable,
    pre-emptable
}

PriorityLevel               ::= INTEGER { spare (0), highest (1), lowest (14), no-priority (15) } (0..15)

-- Q

QCI ::= INTEGER (0..255)

-- R


ReceiveStatusofULPDCPSDUs ::= BIT STRING (SIZE(4096))

Registration-Request    ::= ENUMERATED {
    start,
    stop,
    ...
}

RelativeNarrowbandTxPower ::= SEQUENCE {

    rNTP-PerPRB                         BIT STRING (SIZE(6..110, ...)),
    rNTP-Threshold                      RNTP-Threshold,
    numberOfCellSpecificAntennaPorts    ENUMERATED {one, two, four, ...},
    p-B                                 INTEGER (0..3,...),
    pDCCH-InterferenceImpact            INTEGER (0..4,...),
    -- iE-Extensions                       ProtocolExtensionContainer { { RelativeNarrowbandTxPower-ExtIEs} } OPTIONAL,
    iE-Extensions               IE-Extensions OPTIONAL,
    ...
}

ReportArea ::= ENUMERATED{
    ecgi,
    ...
}

ReportCharacteristics   ::= BIT STRING (SIZE (32))

RNTP-Threshold ::= ENUMERATED {
    minusInfinity,
    minusEleven,
    minusTen,
    minusNine,
    minusEight,
    minusSeven,
    minusSix,
    minusFive,
    minusFour,
    minusThree,
    minusTwo,
    minusOne,
    zero,
    one,
    two,
    three,
    ...
}

RRC-Context ::= OCTET STRING


RadioResourceStatus ::= SEQUENCE {
    dL-GBR-PRB-usage                            DL-GBR-PRB-usage,
    uL-GBR-PRB-usage                            UL-GBR-PRB-usage,
    dL-non-GBR-PRB-usage                        DL-non-GBR-PRB-usage,
    uL-non-GBR-PRB-usage                        UL-non-GBR-PRB-usage,
    dL-Total-PRB-usage                          DL-Total-PRB-usage,
    uL-Total-PRB-usage                          UL-Total-PRB-usage,
    -- iE-Extensions                               ProtocolExtensionContainer { {RadioResourceStatus-ExtIEs} } OPTIONAL,
    iE-Extensions               IE-Extensions OPTIONAL,
    ...
}

DL-GBR-PRB-usage::= INTEGER (0..100)

UL-GBR-PRB-usage::= INTEGER (0..100)

DL-non-GBR-PRB-usage::= INTEGER (0..100)

UL-non-GBR-PRB-usage::= INTEGER (0..100)

DL-Total-PRB-usage::= INTEGER (0..100)

UL-Total-PRB-usage::= INTEGER (0..100)

RadioframeAllocationPeriod ::= ENUMERATED{
    n1,
    n2,
    n4,
    n8,
    n16,
    n32,
    ...
}

RadioframeAllocationOffset ::= INTEGER (0..7, ...)

-- S

S1TNLLoadIndicator ::= SEQUENCE {
    dLS1TNLLoadIndicator            LoadIndicator,
    uLS1TNLLoadIndicator            LoadIndicator,
    -- iE-Extensions                   ProtocolExtensionContainer { { S1TNLLoadIndicator-ExtIEs} } OPTIONAL,
    iE-Extensions               IE-Extensions OPTIONAL,
    ...
}

ServedCellsToActivate::= SEQUENCE (SIZE (1..maxCellineNB)) OF ServedCellsToActivate-Item

ServedCellsToActivate-Item::= SEQUENCE {
    ecgi                        ECGI,
    -- iE-Extensions                   ProtocolExtensionContainer { { ServedCellsToActivate-Item-ExtIEs} } OPTIONAL,
    iE-Extensions               IE-Extensions OPTIONAL,
    ...
}

ServedCellsToModify::= SEQUENCE (SIZE (1..maxCellineNB)) OF IE

ServedCellsToModify-Item::= SEQUENCE {
    old-ecgi                        ECGI,
    servedCellInfo                  ServedCell-Information,
    neighbour-Info                  Neighbour-Information           OPTIONAL,
    -- iE-Extensions                   ProtocolExtensionContainer { { ServedCellsToModify-Item-ExtIEs} } OPTIONAL,
    iE-Extensions               IE-Extensions OPTIONAL,
    ...
}

Old-ECGIs::= SEQUENCE (SIZE (1..maxCellineNB)) OF ECGI

ServedCells ::= SEQUENCE (SIZE (1.. maxCellineNB)) OF ServedCellItem

ServedCellItem ::= SEQUENCE {
    servedCellInfo                  ServedCell-Information,
    neighbour-Info                  Neighbour-Information           OPTIONAL,
    -- iE-Extensions                   ProtocolExtensionContainer { {ServedCell-ExtIEs} } OPTIONAL,
    iE-Extensions               IE-Extensions OPTIONAL,
    ...
}

ServedCell-Information ::= SEQUENCE {
    pCI                 PCI,
    cellId              ECGI,
    tAC                 TAC,
    broadcastPLMNs      BroadcastPLMNs-Item,
    eUTRA-Mode-Info     EUTRA-Mode-Info,
    -- iE-Extensions       ProtocolExtensionContainer { {ServedCell-Information-ExtIEs} } OPTIONAL,
    iE-Extensions               IE-Extensions OPTIONAL,
    ...
}

ShortMAC-I ::= BIT STRING (SIZE(16))

SRVCCOperationPossible ::= ENUMERATED {
    possible,
    ...
}

SubframeAssignment ::= ENUMERATED {
    sa0,
    sa1,
    sa2,
    sa3,
    sa4,
    sa5,
    sa6,
    ...
}

SpecialSubframe-Info ::=        SEQUENCE {
    specialSubframePatterns     SpecialSubframePatterns,
    cyclicPrefixDL              CyclicPrefixDL,
    cyclicPrefixUL              CyclicPrefixUL,
    -- iE-Extensions               ProtocolExtensionContainer { { SpecialSubframe-Info-ExtIEs} } OPTIONAL,
    iE-Extensions               IE-Extensions OPTIONAL,
    ...
}

SpecialSubframePatterns ::= ENUMERATED {
    ssp0,
    ssp1,
    ssp2,
    ssp3,
    ssp4,
    ssp5,
    ssp6,
    ssp7,
    ssp8,
    ...
}

SubscriberProfileIDforRFP ::= INTEGER (1..256)

SubframeAllocation ::= CHOICE {
    oneframe                        Oneframe,
    fourframes                      Fourframes,
    ...
}

-- T

TAC ::= OCTET STRING (SIZE (2))

TargeteNBtoSource-eNBTransparentContainer   ::= OCTET STRING


TimeToWait ::= ENUMERATED {
    v1s,
    v2s,
    v5s,
    v10s,
    v20s,
    v60s,
    ...
}

Time-UE-StayedInCell ::= INTEGER (0..4095)


TraceActivation ::= SEQUENCE {
    eUTRANTraceID                   EUTRANTraceID,
    interfacesToTrace               InterfacesToTrace,
    traceDepth                      TraceDepth,
    traceCollectionEntityIPAddress  TraceCollectionEntityIPAddress,
    -- iE-Extensions                   ProtocolExtensionContainer { {TraceActivation-ExtIEs} } OPTIONAL,
    iE-Extensions               IE-Extensions OPTIONAL,
    ...
}

TraceCollectionEntityIPAddress ::= BIT STRING (SIZE(1..160, ...))

TraceDepth      ::= ENUMERATED {
    minimum,
    medium,
    maximum,
    minimumWithoutVendorSpecificExtension,
    mediumWithoutVendorSpecificExtension,
    maximumWithoutVendorSpecificExtension,
    ...
}

Transmission-Bandwidth ::= ENUMERATED {
        bw6,
        bw15,
        bw25,
        bw50,
        bw75,
        bw100,
        ...
}

TransportLayerAddress           ::= BIT STRING (SIZE(1..160, ...))

TypeOfError ::= ENUMERATED {
    not-understood,
    missing,
    ...
}

-- U

UE-HistoryInformation ::= SEQUENCE (SIZE(1..maxnoofCells)) OF LastVisitedCell-Item


UE-S1AP-ID                  ::= INTEGER (0.. 4294967295)

UE-X2AP-ID                  ::= INTEGER (0..4095) -- Value FFS

UEAggregateMaximumBitRate ::= SEQUENCE {
    uEaggregateMaximumBitRateDownlink   BitRate,
    uEaggregateMaximumBitRateUplink     BitRate,
    -- iE-Extensions                       ProtocolExtensionContainer { {UEAggregate-MaximumBitrate-ExtIEs} } OPTIONAL,
    iE-Extensions               IE-Extensions OPTIONAL,
    ...
}

UESecurityCapabilities ::= SEQUENCE {
    encryptionAlgorithms                EncryptionAlgorithms,
    integrityProtectionAlgorithms       IntegrityProtectionAlgorithms,
    -- iE-Extensions                       ProtocolExtensionContainer { { UESecurityCapabilities-ExtIEs} }     OPTIONAL,
    iE-Extensions               IE-Extensions OPTIONAL,
    ...
}

UE-ContextInformation ::= SEQUENCE {
    mME-UE-S1AP-ID                      UE-S1AP-ID,
    uESecurityCapabilities              UESecurityCapabilities,
    aS-SecurityInformation              AS-SecurityInformation,
    uEaggregateMaximumBitRate           UEAggregateMaximumBitRate,
    subscriberProfileIDforRFP           SubscriberProfileIDforRFP       OPTIONAL,
    e-RABs-ToBeSetup-List               E-RABs-ToBeSetup-List,
    rRC-Context                         RRC-Context,
    handoverRestrictionList             HandoverRestrictionList     OPTIONAL,
    locationReportingInformation        LocationReportingInformation    OPTIONAL,
    -- iE-Extensions                       ProtocolExtensionContainer { {UE-ContextInformation-ExtIEs} } OPTIONAL,
    iE-Extensions               IE-Extensions OPTIONAL,
    ...
}

UL-InterferenceOverloadIndication ::= SEQUENCE (SIZE(1..maxnoofPRBs)) OF UL-InterferenceOverloadIndication-Item

UL-InterferenceOverloadIndication-Item ::= ENUMERATED {
    high-interference,
    medium-interference,
    low-interference,
    ...
}

UL-HighInterferenceIndicationInfo ::= SEQUENCE (SIZE(1..maxCellineNB)) OF UL-HighInterferenceIndicationInfo-Item

UL-HighInterferenceIndicationInfo-Item ::= SEQUENCE {
    target-Cell-ID                  ECGI,
    ul-interferenceindication       UL-HighInterferenceIndication,
    -- iE-Extensions                   ProtocolExtensionContainer { { UL-HighInterferenceIndicationInfo-Item-ExtIEs} } OPTIONAL,
    iE-Extensions               IE-Extensions OPTIONAL,
    ...
}

UL-HighInterferenceIndication ::= BIT STRING (SIZE(1..110, ...))

UE-RLF-Report-Container::= OCTET STRING
-- This IE is a transparent container and shall be encoded as the rlfReport field contained in the UEInformationResponse message as defined in TS 36.331 [9]

-- V
-- W
-- X
-- Y
-- Z

END
